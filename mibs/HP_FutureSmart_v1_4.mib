--  (C) COPYRIGHT HP Inc. 2016
--
--  Future Smart MIB.
--
--  Published in July 2016
--
--  Company names and product names mentioned herein may be
--  trademarks, and/or registered trademarks of their respective
--  companies.
--  
--  Consolidated Future Smart MIB v1.3.
--
--  This MIB describes all the HP propreitary
--  objects supported by Future Smart devices
--  when networked connected using a JetDirect print
--  server.
--
--  This MIB complies with the following RFCs:
--
--  rfc 1157 Simple Network Management Protocol
--  rfc 1155 Structure of Management Information
--
--  Notes:
--
--  1) Objects containing a string which are defined in this MIB use the
--     first two bytes to hold the symbol set used to encode the string.
--     The Roman-8 symbol set has a hex encoding of 0x0115.  Other
--     symbol sets are listed in the PCL 5 Comparison Guide in table
--     C-1 Symbol Set Values.
--
--  2) Some of the objects included are only supported if an accessory
--     is installed.  These accessories include:
--       MIO based accessories
--       SIMM based accessories
--       AT hard disk
--       Paper handling accessories
--       Adobe PostScript accessory
--  3) Supported items on a specific device are based on the device's functions & capabilities.  
FUTURESMART-MIB DEFINITIONS ::= BEGIN
hp OBJECT IDENTIFIER ::= { iso(1) org(3) dod(6) internet(1) private(4) enterprises(1) 11}
dm OBJECT IDENTIFIER ::= { hp nm(2) hpsystem(3) net-peripheral(9) netdm(4) 2}

DisplayString ::= OCTET STRING

device                                 OBJECT IDENTIFIER ::=  { dm 1 } 
device-system                                 OBJECT IDENTIFIER ::=  { device 1 }  

status-system                          OBJECT IDENTIFIER ::=  { device-system 2 }  

test                                   OBJECT IDENTIFIER ::=  { device-system 5 }  

job                                    OBJECT IDENTIFIER ::=  { device-system 6 }  

job-info                               OBJECT IDENTIFIER ::=  { job 5 } 
job-info-accounting                    OBJECT IDENTIFIER ::=  { job-info 28 } 
processing-subsystem                   OBJECT IDENTIFIER ::=  { device 3 } 
pml                                    OBJECT IDENTIFIER ::=  { processing-subsystem 4 } 
accounting                             OBJECT IDENTIFIER ::=  { device-system 16 }  

printer-accounting                     OBJECT IDENTIFIER ::=  { accounting 1 } 
printed-media-usage                    OBJECT IDENTIFIER ::=  { printer-accounting 1 } 
printer-color-accounting               OBJECT IDENTIFIER ::=  { accounting 3 } 
printed-media-color-usage              OBJECT IDENTIFIER ::=  { printer-color-accounting 1 } 
printed-modes-accounting               OBJECT IDENTIFIER ::=  { accounting 4 } 
printed-modes-usage                    OBJECT IDENTIFIER ::=  { printed-modes-accounting 1 } 
source-tray-accounting                 OBJECT IDENTIFIER ::=  { accounting 5 } 
source-tray-usage                      OBJECT IDENTIFIER ::=  { source-tray-accounting 1 } 
destination-bin-accounting             OBJECT IDENTIFIER ::=  { accounting 6 } 
destination-bin-usage                  OBJECT IDENTIFIER ::=  { destination-bin-accounting 1 } 
destination-subsystem                  OBJECT IDENTIFIER ::=  { device 4 } 
print-engine                           OBJECT IDENTIFIER ::=  { destination-subsystem 1 } 
print-media                            OBJECT IDENTIFIER ::=  { print-engine 8 } 
media-size                             OBJECT IDENTIFIER ::=  { print-media 5 } 
background-message                     OBJECT IDENTIFIER ::=  { status-system 37 } 
background-message1                    OBJECT IDENTIFIER ::=  { background-message 1 } 
background-message2                    OBJECT IDENTIFIER ::=  { background-message 2 } 
control-panel-display                  OBJECT IDENTIFIER ::=  { status-system 65 } 
settings-system                        OBJECT IDENTIFIER ::=  { device-system 1 }  

id                                     OBJECT IDENTIFIER ::=  { device-system 3 }  

interface                              OBJECT IDENTIFIER ::=  { device-system 4 }  
imaging                                OBJECT IDENTIFIER   ::= { print-engine 6 }
simm                                   OBJECT IDENTIFIER ::=  { interface 1 } 
simm1                                  OBJECT IDENTIFIER ::=  { simm 1 } 
simm1-bank                             OBJECT IDENTIFIER ::=  { simm1 6 } 
simm1-bank1                            OBJECT IDENTIFIER ::=  { simm1-bank 1 } 
simm1-bank2                            OBJECT IDENTIFIER ::=  { simm1-bank 2 } 
simm2                                  OBJECT IDENTIFIER ::=  { simm 2 } 
simm2-bank                             OBJECT IDENTIFIER ::=  { simm2 6 } 
simm2-bank1                            OBJECT IDENTIFIER ::=  { simm2-bank 1 } 
simm2-bank2                            OBJECT IDENTIFIER ::=  { simm2-bank 2 } 
settings-job                           OBJECT IDENTIFIER ::=  { job 1 } 
operating-system                       OBJECT IDENTIFIER ::=  { device-system 19 }   
phd                                    OBJECT IDENTIFIER   ::= { interface 5 }
phd1                                   OBJECT IDENTIFIER   ::= { phd 1 }
phd2                                   OBJECT IDENTIFIER   ::= { phd 2 }
phd3                                   OBJECT IDENTIFIER   ::= { phd 3 }
phd4                                   OBJECT IDENTIFIER   ::= { phd 4 }
phd5                                    OBJECT IDENTIFIER   ::= { phd 5 }
phd6                                    OBJECT IDENTIFIER   ::= { phd 6 }

pdl                                    OBJECT IDENTIFIER ::=  { processing-subsystem 3 } 
settings-pdl                           OBJECT IDENTIFIER ::=  { pdl 1 } 
status-pdl                             OBJECT IDENTIFIER ::=  { pdl 2 } 
errorlog                               OBJECT IDENTIFIER ::=  { device-system 11 }  

error1                                 OBJECT IDENTIFIER ::=  { errorlog 1 } 
error2                                 OBJECT IDENTIFIER ::=  { errorlog 2 } 
error3                                 OBJECT IDENTIFIER ::=  { errorlog 3 } 
error4                                 OBJECT IDENTIFIER ::=  { errorlog 4 } 
error5                                 OBJECT IDENTIFIER ::=  { errorlog 5 } 
error6                                 OBJECT IDENTIFIER ::=  { errorlog 6 } 
error7                                 OBJECT IDENTIFIER ::=  { errorlog 7 } 
error8                                 OBJECT IDENTIFIER ::=  { errorlog 8 } 
error9                                 OBJECT IDENTIFIER ::=  { errorlog 9 } 
error10                                OBJECT IDENTIFIER ::=  { errorlog 10 } 
error11                                OBJECT IDENTIFIER ::=  { errorlog 11 } 
error12                                OBJECT IDENTIFIER ::=  { errorlog 12 } 
error13                                OBJECT IDENTIFIER ::=  { errorlog 13 } 
error14                                OBJECT IDENTIFIER ::=  { errorlog 14 } 
error15                                OBJECT IDENTIFIER ::=  { errorlog 15 } 
error16                                OBJECT IDENTIFIER ::=  { errorlog 16 } 
error17                                OBJECT IDENTIFIER ::=  { errorlog 17 } 
error18                                OBJECT IDENTIFIER ::=  { errorlog 18 } 
error19                                OBJECT IDENTIFIER ::=  { errorlog 19 } 
error20                                OBJECT IDENTIFIER ::=  { errorlog 20 } 
error21                                OBJECT IDENTIFIER ::=  { errorlog 21 } 
error22                                OBJECT IDENTIFIER ::=  { errorlog 22 } 
error23                                OBJECT IDENTIFIER ::=  { errorlog 23 } 
error24                                OBJECT IDENTIFIER ::=  { errorlog 24 } 
error25                                OBJECT IDENTIFIER ::=  { errorlog 25 } 
error26                                OBJECT IDENTIFIER ::=  { errorlog 26 } 
error27                                OBJECT IDENTIFIER ::=  { errorlog 27 } 
error28                                OBJECT IDENTIFIER ::=  { errorlog 28 } 
error29                                OBJECT IDENTIFIER ::=  { errorlog 29 } 
error30                                OBJECT IDENTIFIER ::=  { errorlog 30 } 
error31                                OBJECT IDENTIFIER ::=  { errorlog 31 } 
error32                                OBJECT IDENTIFIER ::=  { errorlog 32 } 
error33                                OBJECT IDENTIFIER ::=  { errorlog 33 } 
error34                                OBJECT IDENTIFIER ::=  { errorlog 34 } 
error35                                OBJECT IDENTIFIER ::=  { errorlog 35 } 
error36                                OBJECT IDENTIFIER ::=  { errorlog 36 } 
error37                                OBJECT IDENTIFIER ::=  { errorlog 37 } 
error38                                OBJECT IDENTIFIER ::=  { errorlog 38 } 
error39                                OBJECT IDENTIFIER ::=  { errorlog 39 } 
error40                                OBJECT IDENTIFIER ::=  { errorlog 40 } 
error41                                OBJECT IDENTIFIER ::=  { errorlog 41 } 
error42                                OBJECT IDENTIFIER ::=  { errorlog 42 } 
error43                                OBJECT IDENTIFIER ::=  { errorlog 43 } 
error44                                OBJECT IDENTIFIER ::=  { errorlog 44 } 
error45                                OBJECT IDENTIFIER ::=  { errorlog 45 } 
error46                                OBJECT IDENTIFIER ::=  { errorlog 46 } 
error47                                OBJECT IDENTIFIER ::=  { errorlog 47 } 
error48                                OBJECT IDENTIFIER ::=  { errorlog 48 } 
error49                                OBJECT IDENTIFIER ::=  { errorlog 49 } 
error50                                OBJECT IDENTIFIER ::=  { errorlog 50 } 
error51                                OBJECT IDENTIFIER ::=  { errorlog 51 } 
error52                                OBJECT IDENTIFIER ::=  { errorlog 52 } 
error53                                OBJECT IDENTIFIER ::=  { errorlog 53 } 
error54                                OBJECT IDENTIFIER ::=  { errorlog 54 } 
error55                                OBJECT IDENTIFIER ::=  { errorlog 55 } 
error56                                OBJECT IDENTIFIER ::=  { errorlog 56 } 
error57                                OBJECT IDENTIFIER ::=  { errorlog 57 } 
error58                                OBJECT IDENTIFIER ::=  { errorlog 58 } 
error59                                OBJECT IDENTIFIER ::=  { errorlog 59 } 
error60                                OBJECT IDENTIFIER ::=  { errorlog 60 } 
error61                                OBJECT IDENTIFIER ::=  { errorlog 61 } 
error62                                OBJECT IDENTIFIER ::=  { errorlog 62 } 
error63                                OBJECT IDENTIFIER ::=  { errorlog 63 } 
error64                                OBJECT IDENTIFIER ::=  { errorlog 64 } 
error65                                OBJECT IDENTIFIER ::=  { errorlog 65 } 
error66                                OBJECT IDENTIFIER ::=  { errorlog 66 } 
error67                                OBJECT IDENTIFIER ::=  { errorlog 67 } 
error68                                OBJECT IDENTIFIER ::=  { errorlog 68 } 
error69                                OBJECT IDENTIFIER ::=  { errorlog 69 } 
error70                                OBJECT IDENTIFIER ::=  { errorlog 70 } 
error71                                OBJECT IDENTIFIER ::=  { errorlog 71 } 
error72                                OBJECT IDENTIFIER ::=  { errorlog 72 } 
error73                                OBJECT IDENTIFIER ::=  { errorlog 73 } 
error74                                OBJECT IDENTIFIER ::=  { errorlog 74 } 
error75                                OBJECT IDENTIFIER ::=  { errorlog 75 } 
error76                                OBJECT IDENTIFIER ::=  { errorlog 76 } 
error77                                OBJECT IDENTIFIER ::=  { errorlog 77 } 
error78                                OBJECT IDENTIFIER ::=  { errorlog 78 } 
error79                                OBJECT IDENTIFIER ::=  { errorlog 79 } 
error80                                OBJECT IDENTIFIER ::=  { errorlog 80 } 
error81                                OBJECT IDENTIFIER ::=  { errorlog 81 } 
error82                                OBJECT IDENTIFIER ::=  { errorlog 82 } 
error83                                OBJECT IDENTIFIER ::=  { errorlog 83 } 
error84                                OBJECT IDENTIFIER ::=  { errorlog 84 } 
error85                                OBJECT IDENTIFIER ::=  { errorlog 85 } 
error86                                OBJECT IDENTIFIER ::=  { errorlog 86 } 
error87                                OBJECT IDENTIFIER ::=  { errorlog 87 } 
error88                                OBJECT IDENTIFIER ::=  { errorlog 88 } 
error89                                OBJECT IDENTIFIER ::=  { errorlog 89 } 
error90                                OBJECT IDENTIFIER ::=  { errorlog 90 } 
channel                                OBJECT IDENTIFIER ::=  { device 6 } 
display                                OBJECT IDENTIFIER ::=  { status-system 20 } 
display-status                         OBJECT IDENTIFIER ::=  { display 1 } 
web-server                             OBJECT IDENTIFIER ::=  { interface 6 } 
settings-web-server                    OBJECT IDENTIFIER ::=  { web-server 1 } 
pdl-postscript                         OBJECT IDENTIFIER ::=  { pdl 4 } 
webserver-proc-sub                     OBJECT IDENTIFIER ::=  { processing-subsystem 9 } 
settings-webserver                     OBJECT IDENTIFIER ::=  { webserver-proc-sub 1 } 
settings-prt-eng                       OBJECT IDENTIFIER ::=  { print-engine 1 } 
intray                                 OBJECT IDENTIFIER ::=  { print-engine 3 } 
settings-intray                        OBJECT IDENTIFIER ::=  { intray 1 } 
ph                                     OBJECT IDENTIFIER ::=  { print-engine 7 } 
settings-ph                            OBJECT IDENTIFIER ::=  { ph 1 }  
pdl-pcl                                OBJECT IDENTIFIER ::=  { pdl 3 } 
pdl-pdf                                OBJECT IDENTIFIER ::=  { pdl 15 } 
active-print-jobs                      OBJECT IDENTIFIER ::=  { job 2 } 
job-being-parsed                       OBJECT IDENTIFIER ::=  { active-print-jobs 1 } 
job-info-attribute                     OBJECT IDENTIFIER ::=  { job-info 23 } 
held-job                               OBJECT IDENTIFIER ::=  { job 7 } 
held-job-info                          OBJECT IDENTIFIER ::=  { held-job 1 } 
held-job-control                       OBJECT IDENTIFIER ::=  { held-job 2 } 
source-subsystem                       OBJECT IDENTIFIER ::=  { device 2 } 
spooler                                OBJECT IDENTIFIER ::=  { source-subsystem 4 } 
settings-spooler                       OBJECT IDENTIFIER ::=  { spooler 1 } 
pjl                                    OBJECT IDENTIFIER ::=  { processing-subsystem 5 } 
mio                                    OBJECT IDENTIFIER ::=  { interface 3 } 
mio1                                   OBJECT IDENTIFIER ::=  { mio 1 } 
mio4                                   OBJECT IDENTIFIER ::=  { mio 4 } 
usb-interface                          OBJECT IDENTIFIER ::=  { interface 9 } 
usb                                    OBJECT IDENTIFIER ::=  { usb-interface 2 } 
io                                     OBJECT IDENTIFIER ::=  { source-subsystem 1 } 
settings-io                            OBJECT IDENTIFIER ::=  { io 1 } 
ports                                  OBJECT IDENTIFIER ::=  { io 3 } 
port1                                  OBJECT IDENTIFIER ::=  { ports 1 } 
foreign-interface                      OBJECT IDENTIFIER   ::= { interface 8 }
fax-proc-sub                           OBJECT IDENTIFIER   ::= { processing-subsystem 7 }
settings-fax-proc-sub                  OBJECT IDENTIFIER   ::= { fax-proc-sub 1 }
status-fax-proc-sub                    OBJECT IDENTIFIER   ::= { fax-proc-sub 2 }
 

tables                                 OBJECT IDENTIFIER ::=  { device 7 } 
remote-procedure-call                  OBJECT IDENTIFIER ::=  { device-system 13 }  

settings-rpc                           OBJECT IDENTIFIER ::=  { remote-procedure-call 1 } 
status-rpc                             OBJECT IDENTIFIER ::=  { remote-procedure-call 2 } 
file-system                            OBJECT IDENTIFIER ::=  { device-system 10 }  

settings-file-system                   OBJECT IDENTIFIER ::=  { file-system 1 } 
resource-manager                       OBJECT IDENTIFIER ::=  { device-system 12 }  

mass-storage-resources                 OBJECT IDENTIFIER ::=  { resource-manager 3 } 
mass-storage-block-driver              OBJECT IDENTIFIER ::=  { device-system 15 }  

settings-mass-storage-bd               OBJECT IDENTIFIER ::=  { mass-storage-block-driver 1 } 
status-mass-storage-bd                 OBJECT IDENTIFIER ::=  { mass-storage-block-driver 2 } 
settings-print-media                   OBJECT IDENTIFIER ::=  { print-media 1 } 
media-info                             OBJECT IDENTIFIER ::=  { print-media 3 } 
media1                                 OBJECT IDENTIFIER ::=  { media-info 1 } 
media2                                 OBJECT IDENTIFIER ::=  { media-info 2 } 
media3                                 OBJECT IDENTIFIER ::=  { media-info 3 } 
media4                                 OBJECT IDENTIFIER ::=  { media-info 4 } 
media5                                 OBJECT IDENTIFIER ::=  { media-info 5 } 
media6                                 OBJECT IDENTIFIER ::=  { media-info 6 } 
media7                                 OBJECT IDENTIFIER ::=  { media-info 7 } 
media8                                 OBJECT IDENTIFIER ::=  { media-info 8 } 
media9                                 OBJECT IDENTIFIER ::=  { media-info 9 } 
media10                                OBJECT IDENTIFIER ::=  { media-info 10 } 
media11                                OBJECT IDENTIFIER ::=  { media-info 11 } 
media12                                OBJECT IDENTIFIER ::=  { media-info 12 } 
media13                                OBJECT IDENTIFIER ::=  { media-info 13 } 
media14                                OBJECT IDENTIFIER ::=  { media-info 14 } 
media15                                OBJECT IDENTIFIER ::=  { media-info 15 } 
media16                                OBJECT IDENTIFIER ::=  { media-info 16 } 
media17                                OBJECT IDENTIFIER ::=  { media-info 17 } 
media18                                OBJECT IDENTIFIER ::=  { media-info 18 } 
media19                                OBJECT IDENTIFIER ::=  { media-info 19 } 
media20                                OBJECT IDENTIFIER ::=  { media-info 20 } 
media21                                OBJECT IDENTIFIER ::=  { media-info 21 } 
media22                                OBJECT IDENTIFIER ::=  { media-info 22 } 
media23                                OBJECT IDENTIFIER ::=  { media-info 23 } 
media24                                OBJECT IDENTIFIER ::=  { media-info 24 } 
media25                                OBJECT IDENTIFIER ::=  { media-info 25 } 
media26                                OBJECT IDENTIFIER ::=  { media-info 26 } 
media27                                OBJECT IDENTIFIER ::=  { media-info 27 } 
media28                                OBJECT IDENTIFIER ::=  { media-info 28 } 
media29                                OBJECT IDENTIFIER ::=  { media-info 29 } 
media30                                OBJECT IDENTIFIER ::=  { media-info 30 } 
media31                                OBJECT IDENTIFIER ::=  { media-info 31 } 
media32                                OBJECT IDENTIFIER ::=  { media-info 32 } 
media33                                OBJECT IDENTIFIER ::=  { media-info 33 } 
media34                                OBJECT IDENTIFIER ::=  { media-info 34 } 
media35                                OBJECT IDENTIFIER ::=  { media-info 35 } 
media36                                OBJECT IDENTIFIER ::=  { media-info 36 } 
media37                                OBJECT IDENTIFIER ::=  { media-info 37 } 
media38                                OBJECT IDENTIFIER ::=  { media-info 38 } 
media-types                            OBJECT IDENTIFIER ::=  { print-media 8 } 
media-sizes                            OBJECT IDENTIFIER ::=  { print-engine 15 } 
device-configure                       OBJECT IDENTIFIER ::=  { settings-system 32 } 
marking-agent-density                  OBJECT IDENTIFIER ::=  { settings-prt-eng 9 } 
status-prt-eng                         OBJECT IDENTIFIER ::=  { print-engine 2 } 
printer-calibration-dhalf              OBJECT IDENTIFIER ::=  { status-prt-eng 37 } 
printer-cal-dhalf-data                 OBJECT IDENTIFIER ::=  { printer-calibration-dhalf 3 } 
printer-cal-grayaxis                   OBJECT IDENTIFIER ::=  { printer-calibration-dhalf 6 } 
printer-cal-grayaxis-data              OBJECT IDENTIFIER ::=  { printer-calibration-dhalf 7 } 
printer-calibration-cpr                OBJECT IDENTIFIER ::=  { status-prt-eng 38 } 
intrays                                OBJECT IDENTIFIER ::=  { intray 3 } 
intray1                                OBJECT IDENTIFIER ::=  { intrays 1 } 
intray2                                OBJECT IDENTIFIER ::=  { intrays 2 } 
intray3                                OBJECT IDENTIFIER ::=  { intrays 3 } 
intray5                                OBJECT IDENTIFIER ::=  { intrays 5 } 
intray6                                OBJECT IDENTIFIER ::=  { intrays 6 } 
outbin                                 OBJECT IDENTIFIER ::=  { print-engine 4 } 
settings-outbin                        OBJECT IDENTIFIER ::=  { outbin 1 } 
outbins                                OBJECT IDENTIFIER ::=  { outbin 3 } 
outbin1                                OBJECT IDENTIFIER ::=  { outbins 1 } 
marking-agent                          OBJECT IDENTIFIER ::=  { print-engine 5 } 
settings-marking-agent                 OBJECT IDENTIFIER ::=  { marking-agent 1 } 
ph-devices                             OBJECT IDENTIFIER ::=  { ph 3 } 
ph2                                    OBJECT IDENTIFIER ::=  { ph-devices 2 } 
media-modes                            OBJECT IDENTIFIER ::=  { print-media 4 } 
media-counts                           OBJECT IDENTIFIER ::=  { print-media 7 } 
consumables                            OBJECT IDENTIFIER ::=  { print-engine 10 } 
consumables-1                          OBJECT IDENTIFIER ::=  { consumables 1 } 
consumable-status                      OBJECT IDENTIFIER ::=  { consumables-1 1 } 
consumable-string                      OBJECT IDENTIFIER ::=  { consumables 8 } 
consumables-status                     OBJECT IDENTIFIER ::=  { consumables 5 } 
consumables-life                       OBJECT IDENTIFIER ::=  { consumables-status 1 } 
firmware-download                      OBJECT IDENTIFIER ::=  { device-system 18 }  

upgradable-devices                     OBJECT IDENTIFIER ::=  { device-system 20 }  


warninglog                             OBJECT IDENTIFIER   ::= { device-system 22 } 

warning1                 OBJECT IDENTIFIER   ::= { warninglog 1 }
warning2                 OBJECT IDENTIFIER   ::= { warninglog 2 }
warning3                 OBJECT IDENTIFIER   ::= { warninglog 3 }
warning4                 OBJECT IDENTIFIER   ::= { warninglog 4 }
warning5                 OBJECT IDENTIFIER   ::= { warninglog 5 }
warning6                 OBJECT IDENTIFIER   ::= { warninglog 6 }
warning7                 OBJECT IDENTIFIER   ::= { warninglog 7 }
warning8                 OBJECT IDENTIFIER   ::= { warninglog 8 }
warning9                 OBJECT IDENTIFIER   ::= { warninglog 9 }
warning10                OBJECT IDENTIFIER   ::= { warninglog 10 }
warning11                OBJECT IDENTIFIER   ::= { warninglog 11 }
warning12                OBJECT IDENTIFIER   ::= { warninglog 12 }
warning13                OBJECT IDENTIFIER   ::= { warninglog 13 }
warning14                OBJECT IDENTIFIER   ::= { warninglog 14 }
warning15                OBJECT IDENTIFIER   ::= { warninglog 15 }
warning16                OBJECT IDENTIFIER   ::= { warninglog 16 }
warning17                OBJECT IDENTIFIER   ::= { warninglog 17 }
warning18                OBJECT IDENTIFIER   ::= { warninglog 18 }
warning19                OBJECT IDENTIFIER   ::= { warninglog 19 }
warning20                OBJECT IDENTIFIER   ::= { warninglog 20 }
warning21                OBJECT IDENTIFIER   ::= { warninglog 21 }
warning22                OBJECT IDENTIFIER   ::= { warninglog 22 }
warning23                OBJECT IDENTIFIER   ::= { warninglog 23 }
warning24                OBJECT IDENTIFIER   ::= { warninglog 24 }
warning25                OBJECT IDENTIFIER   ::= { warninglog 25 }
warning26                OBJECT IDENTIFIER   ::= { warninglog 26 }
warning27                OBJECT IDENTIFIER   ::= { warninglog 27 }
warning28                OBJECT IDENTIFIER   ::= { warninglog 28 }
warning29                OBJECT IDENTIFIER   ::= { warninglog 29 }
warning30                OBJECT IDENTIFIER   ::= { warninglog 30 }
warning31                OBJECT IDENTIFIER   ::= { warninglog 31 }
warning32                OBJECT IDENTIFIER   ::= { warninglog 32 }
warning33                OBJECT IDENTIFIER   ::= { warninglog 33 }
warning34                OBJECT IDENTIFIER   ::= { warninglog 34 }
warning35                OBJECT IDENTIFIER   ::= { warninglog 35 }
warning36                OBJECT IDENTIFIER   ::= { warninglog 36 }
warning37                OBJECT IDENTIFIER   ::= { warninglog 37 }
warning38                OBJECT IDENTIFIER   ::= { warninglog 38 }
warning39                OBJECT IDENTIFIER   ::= { warninglog 39 }
warning40                OBJECT IDENTIFIER   ::= { warninglog 40 }
warning41                OBJECT IDENTIFIER   ::= { warninglog 41 }
warning42                OBJECT IDENTIFIER   ::= { warninglog 42 }
warning43                OBJECT IDENTIFIER   ::= { warninglog 43 }
warning44                OBJECT IDENTIFIER   ::= { warninglog 44 }
warning45                OBJECT IDENTIFIER   ::= { warninglog 45 }
warning46                OBJECT IDENTIFIER   ::= { warninglog 46 }
warning47                OBJECT IDENTIFIER   ::= { warninglog 47 }
warning48                OBJECT IDENTIFIER   ::= { warninglog 48 }
warning49                OBJECT IDENTIFIER   ::= { warninglog 49 }
warning50                OBJECT IDENTIFIER   ::= { warninglog 50 }
security                 OBJECT IDENTIFIER   ::= { device-system 23 }  
settings-security        OBJECT IDENTIFIER   ::= { security 1 } 
scanner                  OBJECT IDENTIFIER   ::= { source-subsystem 2 }
settings-scanner         OBJECT IDENTIFIER   ::= { scanner 1 } 
status-scanner         OBJECT IDENTIFIER   ::= { scanner 2 }
 print-meter-usage                      OBJECT IDENTIFIER ::=  { printer-accounting 14 } 
scanner-accounting                     OBJECT IDENTIFIER ::=  { accounting 2 } 
scanned-media-usage    OBJECT IDENTIFIER   ::= { scanner-accounting 1 }
settings-system2
       OBJECT IDENTIFIER   ::= { device-system 25}  




-- 1.3.6.1.4.1.11.2.3.9.4.2.1.1.2.17   
date-and-time   OBJECT-TYPE
   SYNTAX          OCTET STRING    
   ACCESS           read-write   
   STATUS            optional   
   DESCRIPTION "A C structure containing the following fields:  typedef
   struct {  
       ubyte yr; /* year: 0 to 99 */  
       ubyte mon; /* month: 1 to 12 */  
       ubyte day; /* day: 1 to 31 */  
       ubyte wday; /* Day of week: 1 to 07 */  
       ubyte hr; /* hour: 0 to 23 */  
       ubyte min; /* minute: 0 to 59 */  
       ubyte sec; /* second: 0 to 59 */  
       } date_t;  
      where ubyte is an unsigned byte (0-255)."
::= { status-system 17 }

-- 1.3.6.1.4.1.11.2.3.9.4.2.1.1.2.100
automatic-daylight-savings   OBJECT-TYPE
   SYNTAX          INTEGER {
                       eOff(1),
                      eOn(2)
               }   
   ACCESS           read-write    
   STATUS            optional   
   DESCRIPTION "Determines whether or not the automatic adjustment for daylight
   savings time is enabled. If it's enabled the device local time
   will be automatically adjusted for DST period."
  
::= { status-system 100 }

-- 1.3.6.1.4.1.11.2.3.9.4.2.1.1.2.101
daylight-savings-start   OBJECT-TYPE
   SYNTAX          OCTET STRING    
   ACCESS           read-write    
   STATUS            optional   
   DESCRIPTION "A C structure containing the following fields:  
       typedef struct {  
	       ubyte hour; /* hour: 0 to 23 */  
	       ubyte weekday; /* weekday: 0(Sunday) to 6 */  
	       ubyte occurrence; /* occurrence in the month: 1 to 5 */  
	       ubyte month; /* month: 1 to 12 */  
       } dst;  
   where ubyte is an unsigned byte (0-255)."
::= { status-system 101 }

-- 1.3.6.1.4.1.11.2.3.9.4.2.1.1.2.102
daylight-savings-end   OBJECT-TYPE
   SYNTAX          OCTET STRING    
   ACCESS           read-write    
   STATUS            optional   
   DESCRIPTION "A C structure containing the following fields:  
       typedef struct {  
	       ubyte hour; /* hour: 0 to 23 */  
	       ubyte weekday; /* weekday: 0(Sunday) to 6 */  
	       ubyte occurrence; /* occurrence in the month: 1 to 5 */  
	       ubyte month; /* month: 1 to 12 */  
       } dst;  
   where ubyte is an unsigned byte (0-255)."
::= { status-system 102 }

-- 1.3.6.1.4.1.11.2.3.9.4.2.1.1.2.103
daylight-savings-offset   OBJECT-TYPE
   SYNTAX          INTEGER    
   ACCESS           read-write    
   STATUS            optional   
   DESCRIPTION "Controls the offset in minutes to be added to the time when DST
   is in effect."
::= { status-system 103 }

-- 1.3.6.1.4.1.11.2.3.9.4.2.1.1.2.104   
daylight-savings-reset   OBJECT-TYPE
   SYNTAX          INTEGER {
                       eResetToDefault(1),
                      eCustomized(2)
               }   
   ACCESS           read-write    
   STATUS            optional   
   DESCRIPTION "This object is used to reset (set back to factory default for
   the current time zone) or read the current status of the DST
   settings. When Set to eResetToDefault, this object can be used
   to reset all the DST related objects back to their factory
   default values. Setting this object with an INTEGER value of
   eCustomized has no effect. When a Get operation is performed on
   this object it will return a value eResetToDefault if all DST
   settings are still set to they factory value. It will return
   eCustomized if any DST parameter has been set to a custom
   value."
::= { status-system 104 }

-- 1.3.6.1.4.1.11.2.3.9.4.2.1.1.2.99   
rtc-time-zone   OBJECT-TYPE
   SYNTAX          INTEGER {
                       eTzDateline(1),
                      eTzSamoa(2),
                      eTzHawaiian(3),
                      eTzAlaskan(4),
                      eTzPacific(5),
                      eTzUSMountain(6),
                      eTzMexico2(7),
                      eTzMountain(8),
                      eTzCentralAmerica(9),
                      eTzCentral(10),
                      eTzMexico(11),
                      eTzCanadaCentral(12),
                      eTzSAPacific(13),
                      eTzEastern(14),
                      eTzUSEastern(15),
                      eTzAtlantic(16),
                      eTzSAWestern(17),
                      eTzPacificSA(18),
                      eTzNewfoundland(19),
                      eTzESouthAmerica(20),
                      eTzSAEastern(21),
                      eTzGreenland(22),
                      eTzMidAtlantic(23),
                      eTzAzores(24),
                      eTzCapeVerde(25),                      
                      eTzGreenwich(26),                      
                      eTzGMT(27),
                      eTzWEurope(28),
                      eTzCentralEurope(29),
                      eTzRomance(30),
                      eTzCentralEuropean(31),
                      eTzWCentralAfrica(32),
                      eTzGTB(33),
                      eTzEeurope(34),
                      eTzEgypt(35),
                      eTzSouthAfrica(36),
                      eTzFLE(37),
                      eTzJerusalem(38),
                      eTzArabic(39),
                      eTzArab(40),
                      eTzRussian(41),
                      eTzEAfrica(42),
                      eTzIran(43),
                      eTzArabian(44),
                      eTzCaucasus(45),
                      eTzAfghanistan(46),
                      eTzEkaterinburg(47),
                      eTzWestAsia(48),
                      eTzIndia(49),
                      eTzNepal(50),
                      eTzNCentralAsia(51),
                      eTzCentralAsia(52),                      
                      eTzSriLanka(53),
                      eTzMyanmar(54),
                      eTzSEAsia(55),
                      eTzNorthAsia(56),
                      eTzChina(57),
                      eTzNorthAsiaEast(58),
                      eTzMalayPeninsula(59),
                      eTzWAustralia(60),
                      eTzTaipei(61),
                      eTzTokyo(62),
                      eTzKorea(63),
                      eTzYakutsk(64),
                      eTzCenAustralia(65),
                      eTzAUSCentral(66),
                      eTzEAustralia(67),
                      eTzAUSEastern(68),
                      eTzWestPacific(69),
                      eTzTasmania(70),
                      eTzVladivostok(71),
                      eTzCentralPacific(72),
                      eTzNewZealand(73),
                      eTzFiji(74),
                      eTzTonga(75)
               }   
   ACCESS           read-write   
   STATUS            optional   
   DESCRIPTION "Controls the time zone, which can be chosen from a list of time
   zones similar to the one used by Microsoft Windows operating
   system: eTzDateline -12:00 International Date Line West
   eTzSamoa -11:00 Midway Island, Samoa eTzHawaiian -10:00 Hawaii
   eTzAlaskan -09:00 Alaska eTzPacific -08:00 Pacific Time (US &
   Canada); Tijuana eTzUSMountain -07:00 Arizona eTzMexico2 -07:00
   Chihuahua, La Paz, Mazatlan eTzMountain -07:00 Mountain Time
   (US & Canada) eTzCentralAmerica -06:00 Central America
   eTzCentral -06:00 Central Time (US & Canada) eTzMexico -06:00
   Guadalajara, Mexico City, Monterrey eTzCanadaCentral -06:00
   Saskatchewan eTzSAPacific -05:00 Bogota, Lima, Quito eTzEastern
   -05:00 Eastern Time (US & Canada) eTz   USE astern -05:00 Indiana
   (East) eTzAtlantic -04:00 Atlantic Time (Canada) eTzSAWestern
   -04:00 Caracas, La Paz eTzPacificSA -04:00 Santiago
   eTzNewfoundland -03:30 Newfoundland eTzESouthAmerica -03:00
   Brasilia eTzSAEastern -03:00 Buenos Aires, Georgetown
   eTzGreenland -03:00 Greenland eTzMidAtlantic -02:00
   Mid-Atlantic eTzAzores -01:00 Azores eTzCapeVerde -01:00 Cape
   Verde Is. eTzGreenwich 00:00 Casablanca, Monrovia eTzGMT 00:00
   Greenwich Mean Time : Dublin, Edinburgh, Lisbon, London
   eTzWEurope +01:00 Amsterdam, Berlin, Bern, Rome, Stockholm,
   Vienna eTzCentralEurope +01:00 Belgrade, Bratislava, Budapest,
   Ljubljana, Prague eTzRomance +01:00 Brussels, Copenhagen,
   Madrid, Paris eTzCentralEuropean +01:00 Sarajevo, Skopje,
   Warsaw, Zagreb eTzWCentralAfrica +01:00 West Central Africa
   eTzGTB +02:00 Athens, Beirut, Istanbul, Minsk eTzEeurope +02:00
   Bucharest eTzEgypt +02:00 Cairo eTzSouthAfrica +02:00 Harare,
   Pretoria eTzFLE +02:00 Helsinki, Kyiv, Riga, Sofia, Tallinn,
   Vilnius eTzJerusalem +02:00 Jerusalem eTzArabic +03:00 Baghdad
   eTzArab +03:00 Kuwait, Riyadh eTzRussian +03:00 Moscow, St.
   Petersburg, Volgograd eTzEAfrica +03:00 Nairobi eTzIran +03:30
   Tehran eTzArabian +04:00 Abu Dhabi, Muscat eTzCaucasus +04:00
   Baku, Tbilisi, Yerevan eTzAfghanistan +04:30 Kabul eTzEkaterinburg
   +05:00 Ekaterinburg eTzWestAsia +05:00
   Islamabad, Karachi, Tashkent eTzIndia +05:30 Chennai, Kolkata,
   Mumbai, New Delhi eTzNepal +05:45 Kathmandu eTzNCentralAsia
   +06:00 Almaty, Novosibirsk eTzCentralAsia +06:00 Astana, Dhaka
   eTzSriLanka +06:00 Sri Jayawardenepura eTzMyanmar +06:30
   Rangoon eTzSEAsia +07:00 Bangkok, Hanoi, Jakarta eTzNorthAsia
   +07:00 Krasnoyarsk eTzChina +08:00 Beijing, Chongqing, Hong
   Kong, Urumqi eTzNorthAsiaEast +08:00 Irkutsk, Ulaan Bataar
   eTzMalayPeninsula +08:00 Kuala Lumpur, Singapore eTzWAustralia
   +08:00 Perth eTzTaipei +08:00 Taipei eTzTokyo +09:00 Osaka,
   Sapporo, Tokyo eTzKorea +09:00 Seoul eTzYakutsk +09:00 Yakutsk
   eTzCenAustralia +09:30 Adelaide eTzAUSCentral +09:30 Darwin
   eTzEAustralia+10:00 Brisbane eTzAUSEastern +10:00 Canberra,
   Melbourne, Sydney eTzWestPacific +10:00 Guam, Port Moresby
   eTzTasmania +10:00 Hobart eTzVladivostok +10:00 Vladivostok
   eTzCentralPacific +11:00 Magadan, Solomon Is., New Caledonia
   eTzNewZealand +12:00 Auckland, Wellington eTzFiji +12:00 Fiji,
   Kamchatka, MarshallIs. eTzTonga +13:00 Nuku'alofa
   INTERACTION SVM_RTC_TIME_ZONE, DATE-AND-TIME (the device local time will be
   affected), DST start and end time. The SysVars
   SVM_DAYLIGHT_SAVINGS_START, SVM_DAYLIGHT_SAVINGS_END and
   SVM_DAYLIGHT_SAVINGS_OFFSET will be erased. PML objects
   DAYLIGHT-SAVINGS-START, DAYLIGHT-SAVINGS-END and
   DAYLIGHT-SAVINGS-OFFSET may change."
   ::= { status-system 99 }

-- 1.3.6.1.4.1.11.2.3.9.4.2.1.1.2.28
time-display   OBJECT-TYPE
   SYNTAX          INTEGER {
                       eTimeDisplayTwelveHour(1),
                      eTimeDisplayTwentyFourHour(2)
               }   
   ACCESS           read-write   
   STATUS            optional   
   DESCRIPTION "Controls front-panel time display format. Set to
   eTimeDisplayTwelveHour for AM/PM display. Set to
   eTimeDisplayTwentyFourHour for military-type display."
::= { status-system 28 }

-- 1.3.6.1.4.1.11.2.3.9.4.2.1.1.1.22
date-display   OBJECT-TYPE
   SYNTAX          INTEGER {
                       eDateDisplayMMDDYY(1),
                      eDateDisplayDDMMYY(2),
                      eDateDisplayYYMMDD(3),
                      eDateDisplayMMM-DD-YYYY(4),
                      eDateDisplayDD-MMM-YYYY(5),
                      eDateDisplayYYYY-MMM-DD(6)
               }   
   ACCESS           read-write    
   STATUS            optional   
   DESCRIPTION "Controls front-panel date display format."
::= { settings-system 22 }

-- 1.3.6.1.4.1.11.2.3.9.4.2.1.1.2.52
localization-languages-supported   OBJECT-TYPE
   SYNTAX          OCTET STRING    
   ACCESS           read-only    
   STATUS            optional   
   DESCRIPTION "The list of languages supported by the device. The languages
   are primarily, but not limited to, two character codes from ISO
   639, each separated by a comma character."
::= { status-system 52 }

-- 1.3.6.1.4.1.11.2.3.9.4.2.1.1.2.53
localization-countries-supported   OBJECT-TYPE
   SYNTAX          OCTET STRING    
   ACCESS           read-only    
   STATUS            optional   
   DESCRIPTION "The list of countries supported by the device. The countries
   are primarily, but not limited to, two character codes from ISO
   3166, each separated by a comma character."
   ::= { status-system 53 }

-- 1.3.6.1.4.1.11.2.3.9.4.2.1.1.23.1.1   
supports-pjl-user-groups   OBJECT-TYPE
   SYNTAX          INTEGER {
                       eFalse(1),
                      eTrue(2)
               }   
   ACCESS           read-only    
   STATUS            optional   
   DESCRIPTION " Returns eTrue if the device is able to process PJL user group
   variables. See the PJL Technical Reference for the proper
   syntax for setting these variables. Because there may be many
   user groups in some environments, this object allows a client
   application to optimize the print job by including user groups
   only when the device is able to process them"
::= { settings-security 1 }

-- 1.3.6.1.4.1.11.2.3.9.4.2.1.1.2.20.1.3   
show-address   OBJECT-TYPE
   SYNTAX          INTEGER {
                       eAuto(3),
                      eOff(1)
               }   
   ACCESS           read-write    
   STATUS            optional   
   DESCRIPTION " If this object is set to eAuto, and the device has an IP
   address, the IP address of the device will be shown with the
   READY message. If this object is set to eOff, the IP address
   will not be shown"
::= { display-status 3 }

-- 1.3.6.1.4.1.11.2.3.9.4.2.1.1.2.38   
error-log-clear   OBJECT-TYPE
   SYNTAX          INTEGER {
                       eClearErrorLog(1)
               }   
   ACCESS           write-only    
   STATUS            optional   
   DESCRIPTION " Setting this object clears all the entries in the error log
   sub-tree "
::= { status-system 38 }

-- 1.3.6.1.4.1.11.2.3.9.4.2.1.1.2.105   
warning-log-clear   OBJECT-TYPE
   SYNTAX          INTEGER {
                       eClearErrorLog(1)
               }   
   ACCESS           write-only    
   STATUS            optional   
   DESCRIPTION " Setting this object clears all the entries in the warning log
   sub-tree"
::= { status-system 105 }

-- 1.3.6.1.4.1.11.2.3.9.4.2.1.1.22.4.1   
warning4-time-stamp   OBJECT-TYPE
   SYNTAX          INTEGER    
   ACCESS           read-only    
   STATUS            optional   
   DESCRIPTION " Contains some sort of time stamp indicating when warning 4
   occurred. Example time stamps include the actual time the
   warning occurred (in seconds since Jan. 1, 1970), and the total
   engine page count. The device POS documents the meaning of the
   time stamp"
::= { warning4 1 }

-- 1.3.6.1.4.1.11.2.3.9.4.2.1.1.11.14.1   
error14-time-stamp   OBJECT-TYPE
   SYNTAX          INTEGER    
   ACCESS           read-only    
   STATUS            optional   
   DESCRIPTION " Contains some sort of time stamp indicating when error 14
   occurred. Example time stamps include the actual time the error
   occurred (in seconds since Jan. 1, 1970), and the total engine
   page count. The device POS documents the meaning of the time
   stamp"
::= { error14 1 }

-- 1.3.6.1.4.1.11.2.3.9.4.2.1.1.11.15.1   
error15-time-stamp   OBJECT-TYPE
   SYNTAX          INTEGER    
   ACCESS           read-only    
   STATUS            optional   
   DESCRIPTION " Contains some sort of time stamp indicating when error 15
   occurred. Example time stamps include the actual time the error
   occurred (in seconds since Jan. 1, 1970), and the total engine
   page count. The device POS documents the meaning of the time
   stamp"
::= { error15 1 }

-- 1.3.6.1.4.1.11.2.3.9.4.2.1.1.11.16.1   
error16-time-stamp   OBJECT-TYPE
   SYNTAX          INTEGER    
   ACCESS           read-only    
   STATUS            optional   
   DESCRIPTION " Contains some sort of time stamp indicating when error 16
   occurred. Example time stamps include the actual time the error
   occurred (in seconds since Jan. 1, 1970), and the total engine
   page count. The device POS documents the meaning of the time
   stamp"
::= { error16 1 }

-- 1.3.6.1.4.1.11.2.3.9.4.2.1.1.11.17.1   
error17-time-stamp   OBJECT-TYPE
   SYNTAX          INTEGER    
   ACCESS           read-only    
   STATUS            optional   
   DESCRIPTION " Contains some sort of time stamp indicating when error 17
   occurred. Example time stamps include the actual time the error
   occurred (in seconds since Jan. 1, 1970), and the total engine
   page count. The device POS documents the meaning of the time
   stamp"
::= { error17 1 }

-- 1.3.6.1.4.1.11.2.3.9.4.2.1.1.11.18.1   
error18-time-stamp   OBJECT-TYPE
   SYNTAX          INTEGER    
   ACCESS           read-only    
   STATUS            optional   
   DESCRIPTION " Contains some sort of time stamp indicating when error 18
   occurred. Example time stamps include the actual time the error
   occurred (in seconds since Jan. 1, 1970), and the total engine
   page count. The device POS documents the meaning of the time
   stamp"
::= { error18 1 }

-- 1.3.6.1.4.1.11.2.3.9.4.2.1.1.11.19.1   
error19-time-stamp   OBJECT-TYPE
   SYNTAX          INTEGER    
   ACCESS           read-only    
   STATUS            optional   
   DESCRIPTION " Contains some sort of time stamp indicating when error 19
   occurred. Example time stamps include the actual time the error
   occurred (in seconds since Jan. 1, 1970), and the total engine
   page count. The device POS documents the meaning of the time
   stamp"
::= { error19 1 }

-- 1.3.6.1.4.1.11.2.3.9.4.2.1.1.11.20.1   
error20-time-stamp   OBJECT-TYPE
   SYNTAX          INTEGER    
   ACCESS           read-only    
   STATUS            optional   
   DESCRIPTION " Contains some sort of time stamp indicating when error 20
   occurred. Example time stamps include the actual time the error
   occurred (in seconds since Jan. 1, 1970), and the total engine
   page count. The device POS documents the meaning of the time
   stamp" 
::= { error20 1 }

-- 1.3.6.1.4.1.11.2.3.9.4.2.1.1.11.21.1   
error21-time-stamp   OBJECT-TYPE
   SYNTAX          INTEGER    
   ACCESS           read-only    
   STATUS            optional   
   DESCRIPTION " Contains some sort of time stamp indicating when error 21
   occurred. Example time stamps include the actual time the error
   occurred (in seconds since Jan. 1, 1970), and the total engine
   page count. The device POS documents the meaning of the time
   stamp"
::= { error21 1 }

-- 1.3.6.1.4.1.11.2.3.9.4.2.1.1.11.22.1   
error22-time-stamp   OBJECT-TYPE
   SYNTAX          INTEGER    
   ACCESS           read-only    
   STATUS            optional   
   DESCRIPTION " Contains some sort of time stamp indicating when error 22
   occurred. Example time stamps include the actual time the error
   occurred (in seconds since Jan. 1, 1970), and the total engine
   page count. The device POS documents the meaning of the time
   stamp"
::= { error22 1 }

-- 1.3.6.1.4.1.11.2.3.9.4.2.1.1.11.23.1   
error23-time-stamp   OBJECT-TYPE
   SYNTAX          INTEGER    
   ACCESS           read-only    
   STATUS            optional   
   DESCRIPTION " Contains some sort of time stamp indicating when error 23
   occurred. Example time stamps include the actual time the error
   occurred (in seconds since Jan. 1, 1970), and the total engine
   page count. The device POS documents the meaning of the time
   stamp"
::= { error23 1 }

-- 1.3.6.1.4.1.11.2.3.9.4.2.1.1.11.24.1   
error24-time-stamp   OBJECT-TYPE
   SYNTAX          INTEGER    
   ACCESS           read-only    
   STATUS            optional   
   DESCRIPTION " Contains some sort of time stamp indicating when error 24
   occurred. Example time stamps include the actual time the error
   occurred (in seconds since Jan. 1, 1970), and the total engine
   page count. The device POS documents the meaning of the time
   stamp"
::= { error24 1 }

-- 1.3.6.1.4.1.11.2.3.9.4.2.1.1.11.25.1   
error25-time-stamp   OBJECT-TYPE
   SYNTAX          INTEGER    
   ACCESS           read-only    
   STATUS            optional   
   DESCRIPTION " Contains some sort of time stamp indicating when error 25
   occurred. Example time stamps include the actual time the error
   occurred (in seconds since Jan. 1, 1970), and the total engine
   page count. The device POS documents the meaning of the time
   stamp"
::= { error25 1 }

-- 1.3.6.1.4.1.11.2.3.9.4.2.1.1.11.26.1   
error26-time-stamp   OBJECT-TYPE
   SYNTAX          INTEGER    
   ACCESS           read-only    
   STATUS            optional   
   DESCRIPTION " Contains some sort of time stamp indicating when error 26
   occurred. Example time stamps include the actual time the error
   occurred (in seconds since Jan. 1, 1970), and the total engine
   page count. The device POS documents the meaning of the time
   stamp"
::= { error26 1 }

-- 1.3.6.1.4.1.11.2.3.9.4.2.1.1.11.27.1   
error27-time-stamp   OBJECT-TYPE
   SYNTAX          INTEGER    
   ACCESS           read-only    
   STATUS            optional   
   DESCRIPTION " Contains some sort of time stamp indicating when error 27
   occurred. Example time stamps include the actual time the error
   occurred (in seconds since Jan. 1, 1970), and the total engine
   page count. The device POS documents the meaning of the time
   stamp"
::= { error27 1 }

-- 1.3.6.1.4.1.11.2.3.9.4.2.1.1.11.28.1   
error28-time-stamp   OBJECT-TYPE
   SYNTAX          INTEGER    
   ACCESS           read-only    
   STATUS            optional   
   DESCRIPTION " Contains some sort of time stamp indicating when error 28
   occurred. Example time stamps include the actual time the error
   occurred (in seconds since Jan. 1, 1970), and the total engine
   page count. The device POS documents the meaning of the time
   stamp"
::= { error28 1 }

-- 1.3.6.1.4.1.11.2.3.9.4.2.1.1.11.29.1   
error29-time-stamp   OBJECT-TYPE
   SYNTAX          INTEGER    
   ACCESS           read-only    
   STATUS            optional   
   DESCRIPTION " Contains some sort of time stamp indicating when error 29
   occurred. Example time stamps include the actual time the error
   occurred (in seconds since Jan. 1, 1970), and the total engine
   page count. The device POS documents the meaning of the time
   stamp"
::= { error29 1 }

-- 1.3.6.1.4.1.11.2.3.9.4.2.1.1.11.30.1   
error30-time-stamp   OBJECT-TYPE
   SYNTAX          INTEGER    
   ACCESS           read-only    
   STATUS            optional   
   DESCRIPTION " Contains some sort of time stamp indicating when error 30
   occurred. Example time stamps include the actual time the error
   occurred (in seconds since Jan. 1, 1970), and the total engine
   page count. The device POS documents the meaning of the time
   stamp"
::= { error30 1 }

-- 1.3.6.1.4.1.11.2.3.9.4.2.1.1.11.31.1   
error31-time-stamp   OBJECT-TYPE
   SYNTAX          INTEGER    
   ACCESS           read-only    
   STATUS            optional   
   DESCRIPTION " Contains some sort of time stamp indicating when error 31
   occurred. Example time stamps include the actual time the error
   occurred (in seconds since Jan. 1, 1970), and the total engine
   page count. The device POS documents the meaning of the time
   stamp"
::= { error31 1 }

-- 1.3.6.1.4.1.11.2.3.9.4.2.1.1.11.32.1   
error32-time-stamp   OBJECT-TYPE
   SYNTAX          INTEGER    
   ACCESS           read-only    
   STATUS            optional   
   DESCRIPTION " Contains some sort of time stamp indicating when error 32
   occurred. Example time stamps include the actual time the error
   occurred (in seconds since Jan. 1, 1970), and the total engine
   page count. The device POS documents the meaning of the time
   stamp"
::= { error32 1 }

-- 1.3.6.1.4.1.11.2.3.9.4.2.1.1.11.33.1   
error33-time-stamp   OBJECT-TYPE
   SYNTAX          INTEGER    
   ACCESS           read-only    
   STATUS            optional   
   DESCRIPTION " Contains some sort of time stamp indicating when error 33
   occurred. Example time stamps include the actual time the error
   occurred (in seconds since Jan. 1, 1970), and the total engine
   page count. The device POS documents the meaning of the time
   stamp"
::= { error33 1 }

-- 1.3.6.1.4.1.11.2.3.9.4.2.1.1.11.34.1   
error34-time-stamp   OBJECT-TYPE
   SYNTAX          INTEGER    
   ACCESS           read-only    
   STATUS            optional   
   DESCRIPTION " Contains some sort of time stamp indicating when error 34
   occurred. Example time stamps include the actual time the error
   occurred (in seconds since Jan. 1, 1970), and the total engine
   page count. The device POS documents the meaning of the time
   stamp"
::= { error34 1 }

-- 1.3.6.1.4.1.11.2.3.9.4.2.1.1.11.35.1   
error35-time-stamp   OBJECT-TYPE
   SYNTAX          INTEGER    
   ACCESS           read-only    
   STATUS            optional   
   DESCRIPTION " Contains some sort of time stamp indicating when error 35
   occurred. Example time stamps include the actual time the error
   occurred (in seconds since Jan. 1, 1970), and the total engine
   page count. The device POS documents the meaning of the time
   stamp"
::= { error35 1 }

-- 1.3.6.1.4.1.11.2.3.9.4.2.1.1.11.36.1   
error36-time-stamp   OBJECT-TYPE
   SYNTAX          INTEGER    
   ACCESS           read-only    
   STATUS            optional   
   DESCRIPTION " Contains some sort of time stamp indicating when error 36
   occurred. Example time stamps include the actual time the error
   occurred (in seconds since Jan. 1, 1970), and the total engine
   page count. The device POS documents the meaning of the time
   stamp"
::= { error36 1 }

-- 1.3.6.1.4.1.11.2.3.9.4.2.1.1.11.37.1   
error37-time-stamp   OBJECT-TYPE
   SYNTAX          INTEGER    
   ACCESS           read-only    
   STATUS            optional   
   DESCRIPTION " Contains some sort of time stamp indicating when error 37
   occurred. Example time stamps include the actual time the error
   occurred (in seconds since Jan. 1, 1970), and the total engine
   page count. The device POS documents the meaning of the time
   stamp"
::= { error37 1 }

-- 1.3.6.1.4.1.11.2.3.9.4.2.1.1.11.38.1   
error38-time-stamp   OBJECT-TYPE
   SYNTAX          INTEGER    
   ACCESS           read-only    
   STATUS            optional   
   DESCRIPTION " Contains some sort of time stamp indicating when error 38
   occurred. Example time stamps include the actual time the error
   occurred (in seconds since Jan. 1, 1970), and the total engine
   page count. The device POS documents the meaning of the time
   stamp"
::= { error38 1 }

-- 1.3.6.1.4.1.11.2.3.9.4.2.1.1.11.39.1   
error39-time-stamp   OBJECT-TYPE
   SYNTAX          INTEGER    
   ACCESS           read-only    
   STATUS            optional   
   DESCRIPTION " Contains some sort of time stamp indicating when error 39
   occurred. Example time stamps include the actual time the error
   occurred (in seconds since Jan. 1, 1970), and the total engine
   page count. The device POS documents the meaning of the time
   stamp"
::= { error39 1 }

-- 1.3.6.1.4.1.11.2.3.9.4.2.1.1.11.40.1   
error40-time-stamp   OBJECT-TYPE
   SYNTAX          INTEGER    
   ACCESS           read-only    
   STATUS            optional   
   DESCRIPTION " Contains some sort of time stamp indicating when error 40
   occurred. Example time stamps include the actual time the error
   occurred (in seconds since Jan. 1, 1970), and the total engine
   page count. The device POS documents the meaning of the time
   stamp"
::= { error40 1 }

-- 1.3.6.1.4.1.11.2.3.9.4.2.1.1.11.41.1   
error41-time-stamp   OBJECT-TYPE
   SYNTAX          INTEGER    
   ACCESS           read-only    
   STATUS            optional   
   DESCRIPTION " Contains some sort of time stamp indicating when error 41
   occurred. Example time stamps include the actual time the error
   occurred (in seconds since Jan. 1, 1970), and the total engine
   page count. The device POS documents the meaning of the time
   stamp"
::= { error41 1 }

-- 1.3.6.1.4.1.11.2.3.9.4.2.1.1.11.42.1   
error42-time-stamp   OBJECT-TYPE
   SYNTAX          INTEGER    
   ACCESS           read-only    
   STATUS            optional   
   DESCRIPTION " Contains some sort of time stamp indicating when error 42
   occurred. Example time stamps include the actual time the error
   occurred (in seconds since Jan. 1, 1970), and the total engine
   page count. The device POS documents the meaning of the time
   stamp"
::= { error42 1 }

-- 1.3.6.1.4.1.11.2.3.9.4.2.1.1.11.43.1   
error43-time-stamp   OBJECT-TYPE
   SYNTAX          INTEGER    
   ACCESS           read-only    
   STATUS            optional   
   DESCRIPTION " Contains some sort of time stamp indicating when error 43
   occurred. Example time stamps include the actual time the error
   occurred (in seconds since Jan. 1, 1970), and the total engine
   page count. The device POS documents the meaning of the time
   stamp"
::= { error43 1 }

-- 1.3.6.1.4.1.11.2.3.9.4.2.1.1.11.44.1   
error44-time-stamp   OBJECT-TYPE
   SYNTAX          INTEGER    
   ACCESS           read-only    
   STATUS            optional   
   DESCRIPTION " Contains some sort of time stamp indicating when error 44
   occurred. Example time stamps include the actual time the error
   occurred (in seconds since Jan. 1, 1970), and the total engine
   page count. The device POS documents the meaning of the time
   stamp"
::= { error44 1 }

-- 1.3.6.1.4.1.11.2.3.9.4.2.1.1.11.45.1   
error45-time-stamp   OBJECT-TYPE
   SYNTAX          INTEGER    
   ACCESS           read-only    
   STATUS            optional   
   DESCRIPTION " Contains some sort of time stamp indicating when error 45
   occurred. Example time stamps include the actual time the error
   occurred (in seconds since Jan. 1, 1970), and the total engine
   page count. The device POS documents the meaning of the time
   stamp"
::= { error45 1 }

-- 1.3.6.1.4.1.11.2.3.9.4.2.1.1.11.46.1   
error46-time-stamp   OBJECT-TYPE
   SYNTAX          INTEGER    
   ACCESS           read-only    
   STATUS            optional   
   DESCRIPTION " Contains some sort of time stamp indicating when error 46
   occurred. Example time stamps include the actual time the error
   occurred (in seconds since Jan. 1, 1970), and the total engine
   page count. The device POS documents the meaning of the time
   stamp"
::= { error46 1 }

-- 1.3.6.1.4.1.11.2.3.9.4.2.1.1.11.47.1   
error47-time-stamp   OBJECT-TYPE
   SYNTAX          INTEGER    
   ACCESS           read-only    
   STATUS            optional   
   DESCRIPTION " Contains some sort of time stamp indicating when error 47
   occurred. Example time stamps include the actual time the error
   occurred (in seconds since Jan. 1, 1970), and the total engine
   page count. The device POS documents the meaning of the time
   stamp"
::= { error47 1 }

-- 1.3.6.1.4.1.11.2.3.9.4.2.1.1.11.48.1   
error48-time-stamp   OBJECT-TYPE
   SYNTAX          INTEGER    
   ACCESS           read-only    
   STATUS            optional   
   DESCRIPTION " Contains some sort of time stamp indicating when error 48
   occurred. Example time stamps include the actual time the error
   occurred (in seconds since Jan. 1, 1970), and the total engine
   page count. The device POS documents the meaning of the time
   stamp"
::= { error48 1 }

-- 1.3.6.1.4.1.11.2.3.9.4.2.1.1.11.49.1   
error49-time-stamp   OBJECT-TYPE
   SYNTAX          INTEGER    
   ACCESS           read-only    
   STATUS            optional   
   DESCRIPTION " Contains some sort of time stamp indicating when error 49
   occurred. Example time stamps include the actual time the error
   occurred (in seconds since Jan. 1, 1970), and the total engine
   page count. The device POS documents the meaning of the time
   stamp"
::= { error49 1 }

-- 1.3.6.1.4.1.11.2.3.9.4.2.1.1.11.50.1   
error50-time-stamp   OBJECT-TYPE
   SYNTAX          INTEGER    
   ACCESS           read-only    
   STATUS            optional   
   DESCRIPTION " Contains some sort of time stamp indicating when error 50
   occurred. Example time stamps include the actual time the error
   occurred (in seconds since Jan. 1, 1970), and the total engine
   page count. The device POS documents the meaning of the time
   stamp"
::= { error50 1 }

-- 1.3.6.1.4.1.11.2.3.9.4.2.1.1.22.1.1   
warning1-time-stamp   OBJECT-TYPE
   SYNTAX          INTEGER    
   ACCESS           read-only    
   STATUS            optional   
   DESCRIPTION " Contains some sort of time stamp indicating when warning 1
   occurred. Example time stamps include the actual time the
   warning occurred (in seconds since Jan. 1, 1970), and the total
   engine page count. The device POS documents the meaning of the
   time stamp"
::= { warning1 1 }

-- 1.3.6.1.4.1.11.2.3.9.4.2.1.1.22.2.1   
warning2-time-stamp   OBJECT-TYPE
   SYNTAX          INTEGER    
   ACCESS           read-only    
   STATUS            optional   
   DESCRIPTION " Contains some sort of time stamp indicating when warning 2
   occurred. Example time stamps include the actual time the
   warning occurred (in seconds since Jan. 1, 1970), and the total
   engine page count. The device POS documents the meaning of the
   time stamp"
::= { warning2 1 }

-- 1.3.6.1.4.1.11.2.3.9.4.2.1.1.22.3.1   
warning3-time-stamp   OBJECT-TYPE
   SYNTAX          INTEGER    
   ACCESS           read-only    
   STATUS            optional   
   DESCRIPTION " Contains some sort of time stamp indicating when warning 3
   occurred. Example time stamps include the actual time the
   warning occurred (in seconds since Jan. 1, 1970), and the total
   engine page count. The device POS documents the meaning of the
   time stamp"
::= { warning3 1 }

-- 1.3.6.1.4.1.11.2.3.9.4.2.1.1.22.33.1   
warning33-time-stamp   OBJECT-TYPE
   SYNTAX          INTEGER    
   ACCESS           read-only    
   STATUS            optional   
   DESCRIPTION " Contains some sort of time stamp indicating when warning 33
   occurred. Example time stamps include the actual time the
   warning occurred (in seconds since Jan. 1, 1970), and the total
   engine page count. The device POS documents the meaning of the
   time stamp"
::= { warning33 1 }

-- 1.3.6.1.4.1.11.2.3.9.4.2.1.1.22.5.1   
warning5-time-stamp   OBJECT-TYPE
   SYNTAX          INTEGER    
   ACCESS           read-only    
   STATUS            optional   
   DESCRIPTION " Contains some sort of time stamp indicating when warning 5
   occurred. Example time stamps include the actual time the
   warning occurred (in seconds since Jan. 1, 1970), and the total
   engine page count. The device POS documents the meaning of the
   time stamp"
::= { warning5 1 }

-- 1.3.6.1.4.1.11.2.3.9.4.2.1.1.22.6.1   
warning6-time-stamp   OBJECT-TYPE
   SYNTAX          INTEGER    
   ACCESS           read-only    
   STATUS            optional   
   DESCRIPTION " Contains some sort of time stamp indicating when warning 6
   occurred. Example time stamps include the actual time the
   warning occurred (in seconds since Jan. 1, 1970), and the total
   engine page count. The device POS documents the meaning of the
   time stamp"
::= { warning6 1 }

-- 1.3.6.1.4.1.11.2.3.9.4.2.1.1.22.7.1   
warning7-time-stamp   OBJECT-TYPE
   SYNTAX          INTEGER    
   ACCESS           read-only    
   STATUS            optional   
   DESCRIPTION " Contains some sort of time stamp indicating when warning 7
   occurred. Example time stamps include the actual time the
   warning occurred (in seconds since Jan. 1, 1970), and the total
   engine page count. The device POS documents the meaning of the
   time stamp"
::= { warning7 1 }

-- 1.3.6.1.4.1.11.2.3.9.4.2.1.1.22.8.1   
warning8-time-stamp   OBJECT-TYPE
   SYNTAX          INTEGER    
   ACCESS           read-only    
   STATUS            optional   
   DESCRIPTION " Contains some sort of time stamp indicating when warning 8
   occurred. Example time stamps include the actual time the
   warning occurred (in seconds since Jan. 1, 1970), and the total
   engine page count. The device POS documents the meaning of the
   time stamp"
::= { warning8 1 }

-- 1.3.6.1.4.1.11.2.3.9.4.2.1.1.22.9.1   
warning9-time-stamp   OBJECT-TYPE
   SYNTAX          INTEGER    
   ACCESS           read-only    
   STATUS            optional   
   DESCRIPTION " Contains some sort of time stamp indicating when warning 9
   occurred. Example time stamps include the actual time the
   warning occurred (in seconds since Jan. 1, 1970), and the total
   engine page count. The device POS documents the meaning of the
   time stamp"
::= { warning9 1 }

-- 1.3.6.1.4.1.11.2.3.9.4.2.1.1.22.10.1   
warning10-time-stamp   OBJECT-TYPE
   SYNTAX          INTEGER    
   ACCESS           read-only    
   STATUS            optional   
   DESCRIPTION " Contains some sort of time stamp indicating when warning 10
   occurred. Example time stamps include the actual time the
   warning occurred (in seconds since Jan. 1, 1970), and the total
   engine page count. The device POS documents the meaning of the
   time stamp"
::= { warning10 1 }

-- 1.3.6.1.4.1.11.2.3.9.4.2.1.1.22.11.1   
warning11-time-stamp   OBJECT-TYPE
   SYNTAX          INTEGER    
   ACCESS           read-only    
   STATUS            optional   
   DESCRIPTION " Contains some sort of time stamp indicating when warning 11
   occurred. Example time stamps include the actual time the
   warning occurred (in seconds since Jan. 1, 1970), and the total
   engine page count. The device POS documents the meaning of the
   time stamp"
::= { warning11 1 }

-- 1.3.6.1.4.1.11.2.3.9.4.2.1.1.22.12.1   
warning12-time-stamp   OBJECT-TYPE
   SYNTAX          INTEGER    
   ACCESS           read-only    
   STATUS            optional   
   DESCRIPTION " Contains some sort of time stamp indicating when warning 12
   occurred. Example time stamps include the actual time the
   warning occurred (in seconds since Jan. 1, 1970), and the total
   engine page count. The device POS documents the meaning of the
   time stamp"
::= { warning12 1 }

-- 1.3.6.1.4.1.11.2.3.9.4.2.1.1.22.13.1   
warning13-time-stamp   OBJECT-TYPE
   SYNTAX          INTEGER    
   ACCESS           read-only    
   STATUS            optional   
   DESCRIPTION " Contains some sort of time stamp indicating when warning 13
   occurred. Example time stamps include the actual time the
   warning occurred (in seconds since Jan. 1, 1970), and the total
   engine page count. The device POS documents the meaning of the
   time stamp"
::= { warning13 1 }

-- 1.3.6.1.4.1.11.2.3.9.4.2.1.1.22.14.1   
warning14-time-stamp   OBJECT-TYPE
   SYNTAX          INTEGER    
   ACCESS           read-only    
   STATUS            optional   
   DESCRIPTION " Contains some sort of time stamp indicating when warning 14
   occurred. Example time stamps include the actual time the
   warning occurred (in seconds since Jan. 1, 1970), and the total
   engine page count. The device POS documents the meaning of the
   time stamp"
::= { warning14 1 }

-- 1.3.6.1.4.1.11.2.3.9.4.2.1.1.22.15.1   
warning15-time-stamp   OBJECT-TYPE
   SYNTAX          INTEGER    
   ACCESS           read-only    
   STATUS            optional   
   DESCRIPTION " Contains some sort of time stamp indicating when warning 15
   occurred. Example time stamps include the actual time the
   warning occurred (in seconds since Jan. 1, 1970), and the total
   engine page count. The device POS documents the meaning of the
   time stamp"
::= { warning15 1 }

-- 1.3.6.1.4.1.11.2.3.9.4.2.1.1.22.16.1   
warning16-time-stamp   OBJECT-TYPE
   SYNTAX          INTEGER    
   ACCESS           read-only    
   STATUS            optional   
   DESCRIPTION " Contains some sort of time stamp indicating when warning 16
   occurred. Example time stamps include the actual time the
   warning occurred (in seconds since Jan. 1, 1970), and the total
   engine page count. The device POS documents the meaning of the
   time stamp"
::= { warning16 1 }

-- 1.3.6.1.4.1.11.2.3.9.4.2.1.1.22.17.1   
warning17-time-stamp   OBJECT-TYPE
   SYNTAX          INTEGER    
   ACCESS           read-only    
   STATUS            optional   
   DESCRIPTION " Contains some sort of time stamp indicating when warning 17
   occurred. Example time stamps include the actual time the
   warning occurred (in seconds since Jan. 1, 1970), and the total
   engine page count. The device POS documents the meaning of the
   time stamp"
::= { warning17 1 }

-- 1.3.6.1.4.1.11.2.3.9.4.2.1.1.22.18.1   
warning18-time-stamp   OBJECT-TYPE
   SYNTAX          INTEGER    
   ACCESS           read-only    
   STATUS            optional   
   DESCRIPTION " Contains some sort of time stamp indicating when warning 18
   occurred. Example time stamps include the actual time the
   warning occurred (in seconds since Jan. 1, 1970), and the total
   engine page count. The device POS documents the meaning of the
   time stamp"
::= { warning18 1 }

-- 1.3.6.1.4.1.11.2.3.9.4.2.1.1.22.19.1   
warning19-time-stamp   OBJECT-TYPE
   SYNTAX          INTEGER    
   ACCESS           read-only    
   STATUS            optional   
   DESCRIPTION " Contains some sort of time stamp indicating when warning 19
   occurred. Example time stamps include the actual time the
   warning occurred (in seconds since Jan. 1, 1970), and the total
   engine page count. The device POS documents the meaning of the
   time stamp"
::= { warning19 1 }

-- 1.3.6.1.4.1.11.2.3.9.4.2.1.1.22.20.1   
warning20-time-stamp   OBJECT-TYPE
   SYNTAX          INTEGER    
   ACCESS           read-only    
   STATUS            optional   
   DESCRIPTION " Contains some sort of time stamp indicating when warning 20
   occurred. Example time stamps include the actual time the
   warning occurred (in seconds since Jan. 1, 1970), and the total
   engine page count. The device POS documents the meaning of the
   time stamp"
::= { warning20 1 }

-- 1.3.6.1.4.1.11.2.3.9.4.2.1.1.22.21.1   
warning21-time-stamp   OBJECT-TYPE
   SYNTAX          INTEGER    
   ACCESS           read-only    
   STATUS            optional   
   DESCRIPTION " Contains some sort of time stamp indicating when warning 21
   occurred. Example time stamps include the actual time the
   warning occurred (in seconds since Jan. 1, 1970), and the total
   engine page count. The device POS documents the meaning of the
   time stamp"
::= { warning21 1 }

-- 1.3.6.1.4.1.11.2.3.9.4.2.1.1.22.22.1   
warning22-time-stamp   OBJECT-TYPE
   SYNTAX          INTEGER    
   ACCESS           read-only    
   STATUS            optional   
   DESCRIPTION " Contains some sort of time stamp indicating when warning 22
   occurred. Example time stamps include the actual time the
   warning occurred (in seconds since Jan. 1, 1970), and the total
   engine page count. The device POS documents the meaning of the
   time stamp"
::= { warning22 1 }

-- 1.3.6.1.4.1.11.2.3.9.4.2.1.1.22.23.1   
warning23-time-stamp   OBJECT-TYPE
   SYNTAX          INTEGER    
   ACCESS           read-only    
   STATUS            optional   
   DESCRIPTION " Contains some sort of time stamp indicating when warning 23
   occurred. Example time stamps include the actual time the
   warning occurred (in seconds since Jan. 1, 1970), and the total
   engine page count. The device POS documents the meaning of the
   time stamp"
::= { warning23 1 }

-- 1.3.6.1.4.1.11.2.3.9.4.2.1.1.22.24.1   
warning24-time-stamp   OBJECT-TYPE
   SYNTAX          INTEGER    
   ACCESS           read-only    
   STATUS            optional   
   DESCRIPTION " Contains some sort of time stamp indicating when warning 24
   occurred. Example time stamps include the actual time the
   warning occurred (in seconds since Jan. 1, 1970), and the total
   engine page count. The device POS documents the meaning of the
   time stamp"
::= { warning24 1 }

-- 1.3.6.1.4.1.11.2.3.9.4.2.1.1.22.25.1   
warning25-time-stamp   OBJECT-TYPE
   SYNTAX          INTEGER    
   ACCESS           read-only    
   STATUS            optional   
   DESCRIPTION " Contains some sort of time stamp indicating when warning 25
   occurred. Example time stamps include the actual time the
   warning occurred (in seconds since Jan. 1, 1970), and the total
   engine page count. The device POS documents the meaning of the
   time stamp"
::= { warning25 1 }

-- 1.3.6.1.4.1.11.2.3.9.4.2.1.1.22.26.1   
warning26-time-stamp   OBJECT-TYPE
   SYNTAX          INTEGER    
   ACCESS           read-only    
   STATUS            optional   
   DESCRIPTION " Contains some sort of time stamp indicating when warning 26
   occurred. Example time stamps include the actual time the
   warning occurred (in seconds since Jan. 1, 1970), and the total
   engine page count. The device POS documents the meaning of the
   time stamp"
::= { warning26 1 }

-- 1.3.6.1.4.1.11.2.3.9.4.2.1.1.22.27.1   
warning27-time-stamp   OBJECT-TYPE
   SYNTAX          INTEGER    
   ACCESS           read-only    
   STATUS            optional   
   DESCRIPTION " Contains some sort of time stamp indicating when warning 27
   occurred. Example time stamps include the actual time the
   warning occurred (in seconds since Jan. 1, 1970), and the total
   engine page count. The device POS documents the meaning of the
   time stamp"
::= { warning27 1 }

-- 1.3.6.1.4.1.11.2.3.9.4.2.1.1.22.28.1   
warning28-time-stamp   OBJECT-TYPE
   SYNTAX          INTEGER    
   ACCESS           read-only    
   STATUS            optional   
   DESCRIPTION " Contains some sort of time stamp indicating when warning 28
   occurred. Example time stamps include the actual time the
   warning occurred (in seconds since Jan. 1, 1970), and the total
   engine page count. The device POS documents the meaning of the
   time stamp"
::= { warning28 1 }

-- 1.3.6.1.4.1.11.2.3.9.4.2.1.1.22.29.1   
warning29-time-stamp   OBJECT-TYPE
   SYNTAX          INTEGER    
   ACCESS           read-only    
   STATUS            optional   
   DESCRIPTION " Contains some sort of time stamp indicating when warning 29
   occurred. Example time stamps include the actual time the
   warning occurred (in seconds since Jan. 1, 1970), and the total
   engine page count. The device POS documents the meaning of the
   time stamp"
::= { warning29 1 }

-- 1.3.6.1.4.1.11.2.3.9.4.2.1.1.22.30.1   
warning30-time-stamp   OBJECT-TYPE
   SYNTAX          INTEGER    
   ACCESS           read-only    
   STATUS            optional   
   DESCRIPTION " Contains some sort of time stamp indicating when warning 30
   occurred. Example time stamps include the actual time the
   warning occurred (in seconds since Jan. 1, 1970), and the total
   engine page count. The device POS documents the meaning of the
   time stamp"
::= { warning30 1 }

-- 1.3.6.1.4.1.11.2.3.9.4.2.1.1.22.31.1   
warning31-time-stamp   OBJECT-TYPE
   SYNTAX          INTEGER    
   ACCESS           read-only    
   STATUS            optional   
   DESCRIPTION " Contains some sort of time stamp indicating when warning 31
   occurred. Example time stamps include the actual time the
   warning occurred (in seconds since Jan. 1, 1970), and the total
   engine page count. The device POS documents the meaning of the
   time stamp"
::= { warning31 1 }

-- 1.3.6.1.4.1.11.2.3.9.4.2.1.1.22.32.1   
warning32-time-stamp   OBJECT-TYPE
   SYNTAX          INTEGER    
   ACCESS           read-only    
   STATUS            optional   
   DESCRIPTION " Contains some sort of time stamp indicating when warning 32
   occurred. Example time stamps include the actual time the
   warning occurred (in seconds since Jan. 1, 1970), and the total
   engine page count. The device POS documents the meaning of the
   time stamp"
::= { warning32 1 }

-- 1.3.6.1.4.1.11.2.3.9.4.2.1.1.22.48.1   
warning48-time-stamp   OBJECT-TYPE
   SYNTAX          INTEGER    
   ACCESS           read-only    
   STATUS            optional   
   DESCRIPTION " Contains some sort of time stamp indicating when warning 48
   occurred. Example time stamps include the actual time the
   warning occurred (in seconds since Jan. 1, 1970), and the total
   engine page count. The device POS documents the meaning of the
   time stamp"
::= { warning48 1 }

-- 1.3.6.1.4.1.11.2.3.9.4.2.1.1.11.13.1   
error13-time-stamp   OBJECT-TYPE
   SYNTAX          INTEGER    
   ACCESS           read-only    
   STATUS            optional   
   DESCRIPTION " Contains some sort of time stamp indicating when error 13
   occurred. Example time stamps include the actual time the error
   occurred (in seconds since Jan. 1, 1970), and the total engine
   page count. The device POS documents the meaning of the time
   stamp"
::= { error13 1 }

-- 1.3.6.1.4.1.11.2.3.9.4.2.1.1.22.35.1   
warning35-time-stamp   OBJECT-TYPE
   SYNTAX          INTEGER    
   ACCESS           read-only    
   STATUS            optional   
   DESCRIPTION " Contains some sort of time stamp indicating when warning 35
   occurred. Example time stamps include the actual time the
   warning occurred (in seconds since Jan. 1, 1970), and the total
   engine page count. The device POS documents the meaning of the
   time stamp"
::= { warning35 1 }

-- 1.3.6.1.4.1.11.2.3.9.4.2.1.1.22.36.1   
warning36-time-stamp   OBJECT-TYPE
   SYNTAX          INTEGER    
   ACCESS           read-only    
   STATUS            optional   
   DESCRIPTION " Contains some sort of time stamp indicating when warning 36
   occurred. Example time stamps include the actual time the
   warning occurred (in seconds since Jan. 1, 1970), and the total
   engine page count. The device POS documents the meaning of the
   time stamp"
::= { warning36 1 }

-- 1.3.6.1.4.1.11.2.3.9.4.2.1.1.22.37.1   
warning37-time-stamp   OBJECT-TYPE
   SYNTAX          INTEGER    
   ACCESS           read-only    
   STATUS            optional   
   DESCRIPTION " Contains some sort of time stamp indicating when warning 37
   occurred. Example time stamps include the actual time the
   warning occurred (in seconds since Jan. 1, 1970), and the total
   engine page count. The device POS documents the meaning of the
   time stamp"
::= { warning37 1 }

-- 1.3.6.1.4.1.11.2.3.9.4.2.1.1.22.38.1   
warning38-time-stamp   OBJECT-TYPE
   SYNTAX          INTEGER    
   ACCESS           read-only    
   STATUS            optional   
   DESCRIPTION " Contains some sort of time stamp indicating when warning 38
   occurred. Example time stamps include the actual time the
   warning occurred (in seconds since Jan. 1, 1970), and the total
   engine page count. The device POS documents the meaning of the
   time stamp"
::= { warning38 1 }

-- 1.3.6.1.4.1.11.2.3.9.4.2.1.1.22.39.1   
warning39-time-stamp   OBJECT-TYPE
   SYNTAX          INTEGER    
   ACCESS           read-only    
   STATUS            optional   
   DESCRIPTION " Contains some sort of time stamp indicating when warning 39
   occurred. Example time stamps include the actual time the
   warning occurred (in seconds since Jan. 1, 1970), and the total
   engine page count. The device POS documents the meaning of the
   time stamp"
::= { warning39 1 }

-- 1.3.6.1.4.1.11.2.3.9.4.2.1.1.22.40.1   
warning40-time-stamp   OBJECT-TYPE
   SYNTAX          INTEGER    
   ACCESS           read-only    
   STATUS            optional   
   DESCRIPTION " Contains some sort of time stamp indicating when warning 40
   occurred. Example time stamps include the actual time the
   warning occurred (in seconds since Jan. 1, 1970), and the total
   engine page count. The device POS documents the meaning of the
   time stamp"
::= { warning40 1 }

-- 1.3.6.1.4.1.11.2.3.9.4.2.1.1.22.41.1   
warning41-time-stamp   OBJECT-TYPE
   SYNTAX          INTEGER    
   ACCESS           read-only    
   STATUS            optional   
   DESCRIPTION " Contains some sort of time stamp indicating when warning 41
   occurred. Example time stamps include the actual time the
   warning occurred (in seconds since Jan. 1, 1970), and the total
   engine page count. The device POS documents the meaning of the
   time stamp"
::= { warning41 1 }

-- 1.3.6.1.4.1.11.2.3.9.4.2.1.1.22.42.1   
warning42-time-stamp   OBJECT-TYPE
   SYNTAX          INTEGER    
   ACCESS           read-only    
   STATUS            optional   
   DESCRIPTION " Contains some sort of time stamp indicating when warning 42
   occurred. Example time stamps include the actual time the
   warning occurred (in seconds since Jan. 1, 1970), and the total
   engine page count. The device POS documents the meaning of the
   time stamp"
::= { warning42 1 }

-- 1.3.6.1.4.1.11.2.3.9.4.2.1.1.22.43.1   
warning43-time-stamp   OBJECT-TYPE
   SYNTAX          INTEGER    
   ACCESS           read-only    
   STATUS            optional   
   DESCRIPTION " Contains some sort of time stamp indicating when warning 43
   occurred. Example time stamps include the actual time the
   warning occurred (in seconds since Jan. 1, 1970), and the total
   engine page count. The device POS documents the meaning of the
   time stamp"
::= { warning43 1 }

-- 1.3.6.1.4.1.11.2.3.9.4.2.1.1.22.44.1   
warning44-time-stamp   OBJECT-TYPE
   SYNTAX          INTEGER    
   ACCESS           read-only    
   STATUS            optional   
   DESCRIPTION " Contains some sort of time stamp indicating when warning 44
   occurred. Example time stamps include the actual time the
   warning occurred (in seconds since Jan. 1, 1970), and the total
   engine page count. The device POS documents the meaning of the
   time stamp"
::= { warning44 1 }

-- 1.3.6.1.4.1.11.2.3.9.4.2.1.1.22.45.1   
warning45-time-stamp   OBJECT-TYPE
   SYNTAX          INTEGER    
   ACCESS           read-only    
   STATUS            optional   
   DESCRIPTION " Contains some sort of time stamp indicating when warning 45
   occurred. Example time stamps include the actual time the
   warning occurred (in seconds since Jan. 1, 1970), and the total
   engine page count. The device POS documents the meaning of the
   time stamp"
::= { warning45 1 }

-- 1.3.6.1.4.1.11.2.3.9.4.2.1.1.22.46.1   
warning46-time-stamp   OBJECT-TYPE
   SYNTAX          INTEGER    
   ACCESS           read-only    
   STATUS            optional   
   DESCRIPTION " Contains some sort of time stamp indicating when warning 46
   occurred. Example time stamps include the actual time the
   warning occurred (in seconds since Jan. 1, 1970), and the total
   engine page count. The device POS documents the meaning of the
   time stamp"
::= { warning46 1 }

-- 1.3.6.1.4.1.11.2.3.9.4.2.1.1.22.47.1   
warning47-time-stamp   OBJECT-TYPE
   SYNTAX          INTEGER    
   ACCESS           read-only    
   STATUS            optional   
   DESCRIPTION " Contains some sort of time stamp indicating when warning 47
   occurred. Example time stamps include the actual time the
   warning occurred (in seconds since Jan. 1, 1970), and the total
   engine page count. The device POS documents the meaning of the
   time stamp"
::= { warning47 1 }

-- 1.3.6.1.4.1.11.2.3.9.4.2.1.1.22.34.1   
warning34-time-stamp   OBJECT-TYPE
   SYNTAX          INTEGER    
   ACCESS           read-only    
   STATUS            optional   
   DESCRIPTION " Contains some sort of time stamp indicating when warning 34
   occurred. Example time stamps include the actual time the
   warning occurred (in seconds since Jan. 1, 1970), and the total
   engine page count. The device POS documents the meaning of the
   time stamp"
::= { warning34 1 }

-- 1.3.6.1.4.1.11.2.3.9.4.2.1.1.22.49.1   
warning49-time-stamp   OBJECT-TYPE
   SYNTAX          INTEGER    
   ACCESS           read-only    
   STATUS            optional   
   DESCRIPTION " Contains some sort of time stamp indicating when warning 49
   occurred. Example time stamps include the actual time the
   warning occurred (in seconds since Jan. 1, 1970), and the total
   engine page count. The device POS documents the meaning of the
   time stamp"
::= { warning49 1 }

-- 1.3.6.1.4.1.11.2.3.9.4.2.1.1.22.50.1   
warning50-time-stamp   OBJECT-TYPE
   SYNTAX          INTEGER    
   ACCESS           read-only    
   STATUS            optional   
   DESCRIPTION " Contains some sort of time stamp indicating when warning 50
   occurred. Example time stamps include the actual time the
   warning occurred (in seconds since Jan. 1, 1970), and the total
   engine page count. The device POS documents the meaning of the
   time stamp"
::= { warning50 1 }

-- 1.3.6.1.4.1.11.2.3.9.4.2.1.1.11.1.1   
error1-time-stamp   OBJECT-TYPE
   SYNTAX          INTEGER    
   ACCESS           read-only    
   STATUS            optional   
   DESCRIPTION " Contains some sort of time stamp indicating when error 1
   occurred. Example time stamps include the actual time the error
   occurred (in seconds since Jan. 1, 1970), and the total engine
   page count. The device POS documents the meaning of the time
   stamp"
::= { error1 1 }

-- 1.3.6.1.4.1.11.2.3.9.4.2.1.1.11.2.1   
error2-time-stamp   OBJECT-TYPE
   SYNTAX          INTEGER    
   ACCESS           read-only    
   STATUS            optional   
   DESCRIPTION " Contains some sort of time stamp indicating when error 2
   occurred. Example time stamps include the actual time the error
   occurred (in seconds since Jan. 1, 1970), and the total engine
   page count. The device POS documents the meaning of the time
   stamp"
::= { error2 1 }

-- 1.3.6.1.4.1.11.2.3.9.4.2.1.1.11.3.1   
error3-time-stamp   OBJECT-TYPE
   SYNTAX          INTEGER    
   ACCESS           read-only    
   STATUS            optional   
   DESCRIPTION " Contains some sort of time stamp indicating when error 3
   occurred. Example time stamps include the actual time the error
   occurred (in seconds since Jan. 1, 1970), and the total engine
   page count. The device POS documents the meaning of the time
   stamp"
::= { error3 1 }

-- 1.3.6.1.4.1.11.2.3.9.4.2.1.1.11.4.1   
error4-time-stamp   OBJECT-TYPE
   SYNTAX          INTEGER    
   ACCESS           read-only    
   STATUS            optional   
   DESCRIPTION " Contains some sort of time stamp indicating when error 4
   occurred. Example time stamps include the actual time the error
   occurred (in seconds since Jan. 1, 1970), and the total engine
   page count. The device POS documents the meaning of the time
   stamp"
::= { error4 1 }

-- 1.3.6.1.4.1.11.2.3.9.4.2.1.1.11.5.1   
error5-time-stamp   OBJECT-TYPE
   SYNTAX          INTEGER    
   ACCESS           read-only    
   STATUS            optional   
   DESCRIPTION " Contains some sort of time stamp indicating when error 5
   occurred. Example time stamps include the actual time the error
   occurred (in seconds since Jan. 1, 1970), and the total engine
   page count. The device POS documents the meaning of the time
   stamp"
::= { error5 1 }

-- 1.3.6.1.4.1.11.2.3.9.4.2.1.1.11.6.1   
error6-time-stamp   OBJECT-TYPE
   SYNTAX          INTEGER    
   ACCESS           read-only    
   STATUS            optional   
   DESCRIPTION " Contains some sort of time stamp indicating when error 6
   occurred. Example time stamps include the actual time the error
   occurred (in seconds since Jan. 1, 1970), and the total engine
   page count. The device POS documents the meaning of the time
   stamp"
::= { error6 1 }

-- 1.3.6.1.4.1.11.2.3.9.4.2.1.1.11.7.1   
error7-time-stamp   OBJECT-TYPE
   SYNTAX          INTEGER    
   ACCESS           read-only    
   STATUS            optional   
   DESCRIPTION " Contains some sort of time stamp indicating when error 7
   occurred. Example time stamps include the actual time the error
   occurred (in seconds since Jan. 1, 1970), and the total engine
   page count. The device POS documents the meaning of the time
   stamp"
::= { error7 1 }

-- 1.3.6.1.4.1.11.2.3.9.4.2.1.1.11.8.1   
error8-time-stamp   OBJECT-TYPE
   SYNTAX          INTEGER    
   ACCESS           read-only    
   STATUS            optional   
   DESCRIPTION " Contains some sort of time stamp indicating when error 8
   occurred. Example time stamps include the actual time the error
   occurred (in seconds since Jan. 1, 1970), and the total engine
   page count. The device POS documents the meaning of the time
   stamp"
::= { error8 1 }

-- 1.3.6.1.4.1.11.2.3.9.4.2.1.1.11.9.1   
error9-time-stamp   OBJECT-TYPE
   SYNTAX          INTEGER    
   ACCESS           read-only    
   STATUS            optional   
   DESCRIPTION " Contains some sort of time stamp indicating when error 9
   occurred. Example time stamps include the actual time the error
   occurred (in seconds since Jan. 1, 1970), and the total engine
   page count. The device POS documents the meaning of the time
   stamp"
::= { error9 1 }

-- 1.3.6.1.4.1.11.2.3.9.4.2.1.1.11.10.1   
error10-time-stamp   OBJECT-TYPE
   SYNTAX          INTEGER    
   ACCESS           read-only    
   STATUS            optional   
   DESCRIPTION " Contains some sort of time stamp indicating when error 10
   occurred. Example time stamps include the actual time the error
   occurred (in seconds since Jan. 1, 1970), and the total engine
   page count. The device POS documents the meaning of the time
   stamp"
::= { error10 1 }

-- 1.3.6.1.4.1.11.2.3.9.4.2.1.1.11.11.1   
error11-time-stamp   OBJECT-TYPE
   SYNTAX          INTEGER    
   ACCESS           read-only    
   STATUS            optional   
   DESCRIPTION " Contains some sort of time stamp indicating when error 11
   occurred. Example time stamps include the actual time the error
   occurred (in seconds since Jan. 1, 1970), and the total engine
   page count. The device POS documents the meaning of the time
   stamp"
::= { error11 1 }

-- 1.3.6.1.4.1.11.2.3.9.4.2.1.1.11.12.1   
error12-time-stamp   OBJECT-TYPE
   SYNTAX          INTEGER    
   ACCESS           read-only    
   STATUS            optional   
   DESCRIPTION " Contains some sort of time stamp indicating when error 12
   occurred. Example time stamps include the actual time the error
   occurred (in seconds since Jan. 1, 1970), and the total engine
   page count. The device POS documents the meaning of the time
   stamp"
::= { error12 1 }

-- 1.3.6.1.4.1.11.2.3.9.4.2.1.1.22.3.2   
warning3-code   OBJECT-TYPE
   SYNTAX          INTEGER    
   ACCESS           read-only    
   STATUS            optional   
   DESCRIPTION " Contains a device specific warning code. Each device POS should
   list what warnings are logged to the warning log and the
   meaning of each supported warning code value"
::= { warning3 2 }

-- 1.3.6.1.4.1.11.2.3.9.4.2.1.1.11.11.2   
error11-code   OBJECT-TYPE
   SYNTAX          INTEGER    
   ACCESS           read-only    
   STATUS            optional   
   DESCRIPTION " Contains a device specific error code. Each device POS should
   list what errors are logged to the error log and the meaning of
   each supported error code value"
::= { error11 2 }

-- 1.3.6.1.4.1.11.2.3.9.4.2.1.1.11.13.2   
error13-code   OBJECT-TYPE
   SYNTAX          INTEGER    
   ACCESS           read-only    
   STATUS            optional   
   DESCRIPTION " Contains a device specific error code. Each device POS should
   list what errors are logged to the error log and the meaning of
   each supported error code value"
::= { error13 2 }

-- 1.3.6.1.4.1.11.2.3.9.4.2.1.1.11.14.2   
error14-code   OBJECT-TYPE
   SYNTAX          INTEGER    
   ACCESS           read-only    
   STATUS            optional   
   DESCRIPTION " Contains a device specific error code. Each device POS should
   list what errors are logged to the error log and the meaning of
   each supported error code value"
::= { error14 2 }

-- 1.3.6.1.4.1.11.2.3.9.4.2.1.1.11.15.2   
error15-code   OBJECT-TYPE
   SYNTAX          INTEGER    
   ACCESS           read-only    
   STATUS            optional   
   DESCRIPTION " Contains a device specific error code. Each device POS should
   list what errors are logged to the error log and the meaning of
   each supported error code value"
::= { error15 2 }

-- 1.3.6.1.4.1.11.2.3.9.4.2.1.1.11.16.2   
error16-code   OBJECT-TYPE
   SYNTAX          INTEGER    
   ACCESS           read-only    
   STATUS            optional   
   DESCRIPTION " Contains a device specific error code. Each device POS should
   list what errors are logged to the error log and the meaning of
   each supported error code value"
::= { error16 2 }

-- 1.3.6.1.4.1.11.2.3.9.4.2.1.1.11.17.2   
error17-code   OBJECT-TYPE
   SYNTAX          INTEGER    
   ACCESS           read-only    
   STATUS            optional   
   DESCRIPTION " Contains a device specific error code. Each device POS should
   list what errors are logged to the error log and the meaning of
   each supported error code value"
::= { error17 2 }

-- 1.3.6.1.4.1.11.2.3.9.4.2.1.1.11.18.2   
error18-code   OBJECT-TYPE
   SYNTAX          INTEGER    
   ACCESS           read-only    
   STATUS            optional   
   DESCRIPTION " Contains a device specific error code. Each device POS should
   list what errors are logged to the error log and the meaning of
   each supported error code value"
::= { error18 2 }

-- 1.3.6.1.4.1.11.2.3.9.4.2.1.1.11.19.2   
error19-code   OBJECT-TYPE
   SYNTAX          INTEGER    
   ACCESS           read-only    
   STATUS            optional   
   DESCRIPTION " Contains a device specific error code. Each device POS should
   list what errors are logged to the error log and the meaning of
   each supported error code value"
::= { error19 2 }

-- 1.3.6.1.4.1.11.2.3.9.4.2.1.1.11.20.2   
error20-code   OBJECT-TYPE
   SYNTAX          INTEGER    
   ACCESS           read-only    
   STATUS            optional   
   DESCRIPTION " Contains a device specific error code. Each device POS should
   list what errors are logged to the error log and the meaning of
   each supported error code value"
::= { error20 2 }

-- 1.3.6.1.4.1.11.2.3.9.4.2.1.1.11.21.2   
error21-code   OBJECT-TYPE
   SYNTAX          INTEGER    
   ACCESS           read-only    
   STATUS            optional   
   DESCRIPTION " Contains a device specific error code. Each device POS should
   list what errors are logged to the error log and the meaning of
   each supported error code value"
::= { error21 2 }

-- 1.3.6.1.4.1.11.2.3.9.4.2.1.1.11.22.2   
error22-code   OBJECT-TYPE
   SYNTAX          INTEGER    
   ACCESS           read-only    
   STATUS            optional   
   DESCRIPTION " Contains a device specific error code. Each device POS should
   list what errors are logged to the error log and the meaning of
   each supported error code value"
::= { error22 2 }

-- 1.3.6.1.4.1.11.2.3.9.4.2.1.1.11.23.2   
error23-code   OBJECT-TYPE
   SYNTAX          INTEGER    
   ACCESS           read-only    
   STATUS            optional   
   DESCRIPTION " Contains a device specific error code. Each device POS should
   list what errors are logged to the error log and the meaning of
   each supported error code value"
::= { error23 2 }

-- 1.3.6.1.4.1.11.2.3.9.4.2.1.1.11.24.2   
error24-code   OBJECT-TYPE
   SYNTAX          INTEGER    
   ACCESS           read-only    
   STATUS            optional   
   DESCRIPTION " Contains a device specific error code. Each device POS should
   list what errors are logged to the error log and the meaning of
   each supported error code value"
::= { error24 2 }

-- 1.3.6.1.4.1.11.2.3.9.4.2.1.1.11.25.2   
error25-code   OBJECT-TYPE
   SYNTAX          INTEGER    
   ACCESS           read-only    
   STATUS            optional   
   DESCRIPTION " Contains a device specific error code. Each device POS should
   list what errors are logged to the error log and the meaning of
   each supported error code value"
::= { error25 2 }

-- 1.3.6.1.4.1.11.2.3.9.4.2.1.1.11.26.2   
error26-code   OBJECT-TYPE
   SYNTAX          INTEGER    
   ACCESS           read-only    
   STATUS            optional   
   DESCRIPTION " Contains a device specific error code. Each device POS should
   list what errors are logged to the error log and the meaning of
   each supported error code value"
::= { error26 2 }

-- 1.3.6.1.4.1.11.2.3.9.4.2.1.1.11.27.2   
error27-code   OBJECT-TYPE
   SYNTAX          INTEGER    
   ACCESS           read-only    
   STATUS            optional   
   DESCRIPTION " Contains a device specific error code. Each device POS should
   list what errors are logged to the error log and the meaning of
   each supported error code value"
::= { error27 2 }

-- 1.3.6.1.4.1.11.2.3.9.4.2.1.1.11.28.2   
error28-code   OBJECT-TYPE
   SYNTAX          INTEGER    
   ACCESS           read-only    
   STATUS            optional   
   DESCRIPTION " Contains a device specific error code. Each device POS should
   list what errors are logged to the error log and the meaning of
   each supported error code value"
::= { error28 2 }

-- 1.3.6.1.4.1.11.2.3.9.4.2.1.1.11.29.2   
error29-code   OBJECT-TYPE
   SYNTAX          INTEGER    
   ACCESS           read-only    
   STATUS            optional   
   DESCRIPTION " Contains a device specific error code. Each device POS should
   list what errors are logged to the error log and the meaning of
   each supported error code value"
::= { error29 2 }

-- 1.3.6.1.4.1.11.2.3.9.4.2.1.1.11.30.2   
error30-code   OBJECT-TYPE
   SYNTAX          INTEGER    
   ACCESS           read-only    
   STATUS            optional   
   DESCRIPTION " Contains a device specific error code. Each device POS should
   list what errors are logged to the error log and the meaning of
   each supported error code value"
::= { error30 2 }

-- 1.3.6.1.4.1.11.2.3.9.4.2.1.1.11.31.2   
error31-code   OBJECT-TYPE
   SYNTAX          INTEGER    
   ACCESS           read-only    
   STATUS            optional   
   DESCRIPTION " Contains a device specific error code. Each device POS should
   list what errors are logged to the error log and the meaning of
   each supported error code value"
::= { error31 2 }

-- 1.3.6.1.4.1.11.2.3.9.4.2.1.1.11.32.2   
error32-code   OBJECT-TYPE
   SYNTAX          INTEGER    
   ACCESS           read-only    
   STATUS            optional   
   DESCRIPTION " Contains a device specific error code. Each device POS should
   list what errors are logged to the error log and the meaning of
   each supported error code value"
::= { error32 2 }

-- 1.3.6.1.4.1.11.2.3.9.4.2.1.1.11.33.2   
error33-code   OBJECT-TYPE
   SYNTAX          INTEGER    
   ACCESS           read-only    
   STATUS            optional   
   DESCRIPTION " Contains a device specific error code. Each device POS should
   list what errors are logged to the error log and the meaning of
   each supported error code value"
::= { error33 2 }

-- 1.3.6.1.4.1.11.2.3.9.4.2.1.1.11.34.2   
error34-code   OBJECT-TYPE
   SYNTAX          INTEGER    
   ACCESS           read-only    
   STATUS            optional   
   DESCRIPTION " Contains a device specific error code. Each device POS should
   list what errors are logged to the error log and the meaning of
   each supported error code value"
::= { error34 2 }

-- 1.3.6.1.4.1.11.2.3.9.4.2.1.1.11.35.2   
error35-code   OBJECT-TYPE
   SYNTAX          INTEGER    
   ACCESS           read-only    
   STATUS            optional   
   DESCRIPTION " Contains a device specific error code. Each device POS should
   list what errors are logged to the error log and the meaning of
   each supported error code value"
::= { error35 2 }

-- 1.3.6.1.4.1.11.2.3.9.4.2.1.1.11.36.2   
error36-code   OBJECT-TYPE
   SYNTAX          INTEGER    
   ACCESS           read-only    
   STATUS            optional   
   DESCRIPTION " Contains a device specific error code. Each device POS should
   list what errors are logged to the error log and the meaning of
   each supported error code value"
::= { error36 2 }

-- 1.3.6.1.4.1.11.2.3.9.4.2.1.1.11.37.2   
error37-code   OBJECT-TYPE
   SYNTAX          INTEGER    
   ACCESS           read-only    
   STATUS            optional   
   DESCRIPTION " Contains a device specific error code. Each device POS should
   list what errors are logged to the error log and the meaning of
   each supported error code value"
::= { error37 2 }

-- 1.3.6.1.4.1.11.2.3.9.4.2.1.1.11.38.2   
error38-code   OBJECT-TYPE
   SYNTAX          INTEGER    
   ACCESS           read-only    
   STATUS            optional   
   DESCRIPTION " Contains a device specific error code. Each device POS should
   list what errors are logged to the error log and the meaning of
   each supported error code value"
::= { error38 2 }

-- 1.3.6.1.4.1.11.2.3.9.4.2.1.1.11.39.2   
error39-code   OBJECT-TYPE
   SYNTAX          INTEGER    
   ACCESS           read-only    
   STATUS            optional   
   DESCRIPTION " Contains a device specific error code. Each device POS should
   list what errors are logged to the error log and the meaning of
   each supported error code value"
::= { error39 2 }

-- 1.3.6.1.4.1.11.2.3.9.4.2.1.1.11.40.2   
error40-code   OBJECT-TYPE
   SYNTAX          INTEGER    
   ACCESS           read-only    
   STATUS            optional   
   DESCRIPTION " Contains a device specific error code. Each device POS should
   list what errors are logged to the error log and the meaning of
   each supported error code value"
::= { error40 2 }

-- 1.3.6.1.4.1.11.2.3.9.4.2.1.1.11.41.2   
error41-code   OBJECT-TYPE
   SYNTAX          INTEGER    
   ACCESS           read-only    
   STATUS            optional   
   DESCRIPTION " Contains a device specific error code. Each device POS should
   list what errors are logged to the error log and the meaning of
   each supported error code value"
::= { error41 2 }

-- 1.3.6.1.4.1.11.2.3.9.4.2.1.1.11.42.2   
error42-code   OBJECT-TYPE
   SYNTAX          INTEGER    
   ACCESS           read-only    
   STATUS            optional   
   DESCRIPTION " Contains a device specific error code. Each device POS should
   list what errors are logged to the error log and the meaning of
   each supported error code value"
::= { error42 2 }

-- 1.3.6.1.4.1.11.2.3.9.4.2.1.1.11.43.2   
error43-code   OBJECT-TYPE
   SYNTAX          INTEGER    
   ACCESS           read-only    
   STATUS            optional   
   DESCRIPTION " Contains a device specific error code. Each device POS should
   list what errors are logged to the error log and the meaning of
   each supported error code value"
::= { error43 2 }

-- 1.3.6.1.4.1.11.2.3.9.4.2.1.1.11.44.2   
error44-code   OBJECT-TYPE
   SYNTAX          INTEGER    
   ACCESS           read-only    
   STATUS            optional   
   DESCRIPTION " Contains a device specific error code. Each device POS should
   list what errors are logged to the error log and the meaning of
   each supported error code value"
::= { error44 2 }

-- 1.3.6.1.4.1.11.2.3.9.4.2.1.1.11.45.2   
error45-code   OBJECT-TYPE
   SYNTAX          INTEGER    
   ACCESS           read-only    
   STATUS            optional   
   DESCRIPTION " Contains a device specific error code. Each device POS should
   list what errors are logged to the error log and the meaning of
   each supported error code value"
::= { error45 2 }

-- 1.3.6.1.4.1.11.2.3.9.4.2.1.1.11.46.2   
error46-code   OBJECT-TYPE
   SYNTAX          INTEGER    
   ACCESS           read-only    
   STATUS            optional   
   DESCRIPTION " Contains a device specific error code. Each device POS should
   list what errors are logged to the error log and the meaning of
   each supported error code value"
::= { error46 2 }

-- 1.3.6.1.4.1.11.2.3.9.4.2.1.1.11.47.2   
error47-code   OBJECT-TYPE
   SYNTAX          INTEGER    
   ACCESS           read-only    
   STATUS            optional   
   DESCRIPTION " Contains a device specific error code. Each device POS should
   list what errors are logged to the error log and the meaning of
   each supported error code value"
::= { error47 2 }

-- 1.3.6.1.4.1.11.2.3.9.4.2.1.1.11.48.2   
error48-code   OBJECT-TYPE
   SYNTAX          INTEGER    
   ACCESS           read-only    
   STATUS            optional   
   DESCRIPTION " Contains a device specific error code. Each device POS should
   list what errors are logged to the error log and the meaning of
   each supported error code value"
::= { error48 2 }

-- 1.3.6.1.4.1.11.2.3.9.4.2.1.1.11.49.2   
error49-code   OBJECT-TYPE
   SYNTAX          INTEGER    
   ACCESS           read-only    
   STATUS            optional   
   DESCRIPTION " Contains a device specific error code. Each device POS should
   list what errors are logged to the error log and the meaning of
   each supported error code value"
::= { error49 2 }

-- 1.3.6.1.4.1.11.2.3.9.4.2.1.1.11.50.2   
error50-code   OBJECT-TYPE
   SYNTAX          INTEGER    
   ACCESS           read-only    
   STATUS            optional   
   DESCRIPTION " Contains a device specific error code. Each device POS should
   list what errors are logged to the error log and the meaning of
   each supported error code value"
::= { error50 2 }

-- 1.3.6.1.4.1.11.2.3.9.4.2.1.1.22.1.2   
warning1-code   OBJECT-TYPE
   SYNTAX          INTEGER    
   ACCESS           read-only    
   STATUS            optional   
   DESCRIPTION " Contains a device specific warning code. Each device POS should
   list what warnings are logged to the warning log and the
   meaning of each supported warning code value"
::= { warning1 2 }

-- 1.3.6.1.4.1.11.2.3.9.4.2.1.1.22.2.2   
warning2-code   OBJECT-TYPE
   SYNTAX          INTEGER    
   ACCESS           read-only    
   STATUS            optional   
   DESCRIPTION " Contains a device specific warning code. Each device POS should
   list what warnings are logged to the warning log and the
   meaning of each supported warning code value"
::= { warning2 2 }

-- 1.3.6.1.4.1.11.2.3.9.4.2.1.1.22.32.2   
warning32-code   OBJECT-TYPE
   SYNTAX          INTEGER    
   ACCESS           read-only    
   STATUS            optional   
   DESCRIPTION " Contains a device specific warning code. Each device POS should
   list what warnings are logged to the warning log and the
   meaning of each supported warning code value"
::= { warning32 2 }

-- 1.3.6.1.4.1.11.2.3.9.4.2.1.1.22.4.2   
warning4-code   OBJECT-TYPE
   SYNTAX          INTEGER    
   ACCESS           read-only    
   STATUS            optional   
   DESCRIPTION " Contains a device specific warning code. Each device POS should
   list what warnings are logged to the warning log and the
   meaning of each supported warning code value"
::= { warning4 2 }

-- 1.3.6.1.4.1.11.2.3.9.4.2.1.1.22.5.2   
warning5-code   OBJECT-TYPE
   SYNTAX          INTEGER    
   ACCESS           read-only    
   STATUS            optional   
   DESCRIPTION " Contains a device specific warning code. Each device POS should
   list what warnings are logged to the warning log and the
   meaning of each supported warning code value"
::= { warning5 2 }

-- 1.3.6.1.4.1.11.2.3.9.4.2.1.1.22.6.2   
warning6-code   OBJECT-TYPE
   SYNTAX          INTEGER    
   ACCESS           read-only    
   STATUS            optional   
   DESCRIPTION " Contains a device specific warning code. Each device POS should
   list what warnings are logged to the warning log and the
   meaning of each supported warning code value"
::= { warning6 2 }

-- 1.3.6.1.4.1.11.2.3.9.4.2.1.1.22.7.2   
warning7-code   OBJECT-TYPE
   SYNTAX          INTEGER    
   ACCESS           read-only    
   STATUS            optional   
   DESCRIPTION " Contains a device specific warning code. Each device POS should
   list what warnings are logged to the warning log and the
   meaning of each supported warning code value"
::= { warning7 2 }

-- 1.3.6.1.4.1.11.2.3.9.4.2.1.1.22.8.2   
warning8-code   OBJECT-TYPE
   SYNTAX          INTEGER    
   ACCESS           read-only    
   STATUS            optional   
   DESCRIPTION " Contains a device specific warning code. Each device POS should
   list what warnings are logged to the warning log and the
   meaning of each supported warning code value"
::= { warning8 2 }

-- 1.3.6.1.4.1.11.2.3.9.4.2.1.1.22.9.2   
warning9-code   OBJECT-TYPE
   SYNTAX          INTEGER    
   ACCESS           read-only    
   STATUS            optional   
   DESCRIPTION " Contains a device specific warning code. Each device POS should
   list what warnings are logged to the warning log and the
   meaning of each supported warning code value"
::= { warning9 2 }

-- 1.3.6.1.4.1.11.2.3.9.4.2.1.1.22.10.2   
warning10-code   OBJECT-TYPE
   SYNTAX          INTEGER    
   ACCESS           read-only    
   STATUS            optional   
   DESCRIPTION " Contains a device specific warning code. Each device POS should
   list what warnings are logged to the warning log and the
   meaning of each supported warning code value"
::= { warning10 2 }

-- 1.3.6.1.4.1.11.2.3.9.4.2.1.1.22.11.2   
warning11-code   OBJECT-TYPE
   SYNTAX          INTEGER    
   ACCESS           read-only    
   STATUS            optional   
   DESCRIPTION " Contains a device specific warning code. Each device POS should
   list what warnings are logged to the warning log and the
   meaning of each supported warning code value"
::= { warning11 2 }

-- 1.3.6.1.4.1.11.2.3.9.4.2.1.1.22.12.2   
warning12-code   OBJECT-TYPE
   SYNTAX          INTEGER    
   ACCESS           read-only    
   STATUS            optional   
   DESCRIPTION " Contains a device specific warning code. Each device POS should
   list what warnings are logged to the warning log and the
   meaning of each supported warning code value"
::= { warning12 2 }

-- 1.3.6.1.4.1.11.2.3.9.4.2.1.1.22.13.2   
warning13-code   OBJECT-TYPE
   SYNTAX          INTEGER    
   ACCESS           read-only    
   STATUS            optional   
   DESCRIPTION " Contains a device specific warning code. Each device POS should
   list what warnings are logged to the warning log and the
   meaning of each supported warning code value"
::= { warning13 2 }

-- 1.3.6.1.4.1.11.2.3.9.4.2.1.1.22.14.2   
warning14-code   OBJECT-TYPE
   SYNTAX          INTEGER    
   ACCESS           read-only    
   STATUS            optional   
   DESCRIPTION " Contains a device specific warning code. Each device POS should
   list what warnings are logged to the warning log and the
   meaning of each supported warning code value"
::= { warning14 2 }

-- 1.3.6.1.4.1.11.2.3.9.4.2.1.1.22.15.2   
warning15-code   OBJECT-TYPE
   SYNTAX          INTEGER    
   ACCESS           read-only    
   STATUS            optional   
   DESCRIPTION " Contains a device specific warning code. Each device POS should
   list what warnings are logged to the warning log and the
   meaning of each supported warning code value"
::= { warning15 2 }

-- 1.3.6.1.4.1.11.2.3.9.4.2.1.1.22.16.2   
warning16-code   OBJECT-TYPE
   SYNTAX          INTEGER    
   ACCESS           read-only    
   STATUS            optional   
   DESCRIPTION " Contains a device specific warning code. Each device POS should
   list what warnings are logged to the warning log and the
   meaning of each supported warning code value"
::= { warning16 2 }

-- 1.3.6.1.4.1.11.2.3.9.4.2.1.1.22.17.2   
warning17-code   OBJECT-TYPE
   SYNTAX          INTEGER    
   ACCESS           read-only    
   STATUS            optional   
   DESCRIPTION " Contains a device specific warning code. Each device POS should
   list what warnings are logged to the warning log and the
   meaning of each supported warning code value"
::= { warning17 2 }

-- 1.3.6.1.4.1.11.2.3.9.4.2.1.1.22.18.2   
warning18-code   OBJECT-TYPE
   SYNTAX          INTEGER    
   ACCESS           read-only    
   STATUS            optional   
   DESCRIPTION " Contains a device specific warning code. Each device POS should
   list what warnings are logged to the warning log and the
   meaning of each supported warning code value"
::= { warning18 2 }

-- 1.3.6.1.4.1.11.2.3.9.4.2.1.1.22.19.2   
warning19-code   OBJECT-TYPE
   SYNTAX          INTEGER    
   ACCESS           read-only    
   STATUS            optional   
   DESCRIPTION " Contains a device specific warning code. Each device POS should
   list what warnings are logged to the warning log and the
   meaning of each supported warning code value"
::= { warning19 2 }

-- 1.3.6.1.4.1.11.2.3.9.4.2.1.1.22.20.2   
warning20-code   OBJECT-TYPE
   SYNTAX          INTEGER    
   ACCESS           read-only    
   STATUS            optional   
   DESCRIPTION " Contains a device specific warning code. Each device POS should
   list what warnings are logged to the warning log and the
   meaning of each supported warning code value"
::= { warning20 2 }

-- 1.3.6.1.4.1.11.2.3.9.4.2.1.1.22.21.2   
warning21-code   OBJECT-TYPE
   SYNTAX          INTEGER    
   ACCESS           read-only    
   STATUS            optional   
   DESCRIPTION " Contains a device specific warning code. Each device POS should
   list what warnings are logged to the warning log and the
   meaning of each supported warning code value"
::= { warning21 2 }

-- 1.3.6.1.4.1.11.2.3.9.4.2.1.1.22.22.2   
warning22-code   OBJECT-TYPE
   SYNTAX          INTEGER    
   ACCESS           read-only    
   STATUS            optional   
   DESCRIPTION " Contains a device specific warning code. Each device POS should
   list what warnings are logged to the warning log and the
   meaning of each supported warning code value"
::= { warning22 2 }

-- 1.3.6.1.4.1.11.2.3.9.4.2.1.1.22.23.2   
warning23-code   OBJECT-TYPE
   SYNTAX          INTEGER    
   ACCESS           read-only    
   STATUS            optional   
   DESCRIPTION " Contains a device specific warning code. Each device POS should
   list what warnings are logged to the warning log and the
   meaning of each supported warning code value"
::= { warning23 2 }

-- 1.3.6.1.4.1.11.2.3.9.4.2.1.1.22.24.2   
warning24-code   OBJECT-TYPE
   SYNTAX          INTEGER    
   ACCESS           read-only    
   STATUS            optional   
   DESCRIPTION " Contains a device specific warning code. Each device POS should
   list what warnings are logged to the warning log and the
   meaning of each supported warning code value"
::= { warning24 2 }

-- 1.3.6.1.4.1.11.2.3.9.4.2.1.1.22.25.2   
warning25-code   OBJECT-TYPE
   SYNTAX          INTEGER    
   ACCESS           read-only    
   STATUS            optional   
   DESCRIPTION " Contains a device specific warning code. Each device POS should
   list what warnings are logged to the warning log and the
   meaning of each supported warning code value"
::= { warning25 2 }

-- 1.3.6.1.4.1.11.2.3.9.4.2.1.1.22.26.2   
warning26-code   OBJECT-TYPE
   SYNTAX          INTEGER    
   ACCESS           read-only    
   STATUS            optional   
   DESCRIPTION " Contains a device specific warning code. Each device POS should
   list what warnings are logged to the warning log and the
   meaning of each supported warning code value"
::= { warning26 2 }

-- 1.3.6.1.4.1.11.2.3.9.4.2.1.1.22.27.2   
warning27-code   OBJECT-TYPE
   SYNTAX          INTEGER    
   ACCESS           read-only    
   STATUS            optional   
   DESCRIPTION " Contains a device specific warning code. Each device POS should
   list what warnings are logged to the warning log and the
   meaning of each supported warning code value"
::= { warning27 2 }

-- 1.3.6.1.4.1.11.2.3.9.4.2.1.1.22.28.2   
warning28-code   OBJECT-TYPE
   SYNTAX          INTEGER    
   ACCESS           read-only    
   STATUS            optional   
   DESCRIPTION " Contains a device specific warning code. Each device POS should
   list what warnings are logged to the warning log and the
   meaning of each supported warning code value"
::= { warning28 2 }

-- 1.3.6.1.4.1.11.2.3.9.4.2.1.1.22.29.2   
warning29-code   OBJECT-TYPE
   SYNTAX          INTEGER    
   ACCESS           read-only    
   STATUS            optional   
   DESCRIPTION " Contains a device specific warning code. Each device POS should
   list what warnings are logged to the warning log and the
   meaning of each supported warning code value"
::= { warning29 2 }

-- 1.3.6.1.4.1.11.2.3.9.4.2.1.1.22.30.2   
warning30-code   OBJECT-TYPE
   SYNTAX          INTEGER    
   ACCESS           read-only    
   STATUS            optional   
   DESCRIPTION " Contains a device specific warning code. Each device POS should
   list what warnings are logged to the warning log and the
   meaning of each supported warning code value"
::= { warning30 2 }

-- 1.3.6.1.4.1.11.2.3.9.4.2.1.1.22.31.2   
warning31-code   OBJECT-TYPE
   SYNTAX          INTEGER    
   ACCESS           read-only    
   STATUS            optional   
   DESCRIPTION " Contains a device specific warning code. Each device POS should
   list what warnings are logged to the warning log and the
   meaning of each supported warning code value"
::= { warning31 2 }

-- 1.3.6.1.4.1.11.2.3.9.4.2.1.1.22.47.2   
warning47-code   OBJECT-TYPE
   SYNTAX          INTEGER    
   ACCESS           read-only    
   STATUS            optional   
   DESCRIPTION " Contains a device specific warning code. Each device POS should
   list what warnings are logged to the warning log and the
   meaning of each supported warning code value"
::= { warning47 2 }

-- 1.3.6.1.4.1.11.2.3.9.4.2.1.1.11.10.2   
error10-code   OBJECT-TYPE
   SYNTAX          INTEGER    
   ACCESS           read-only    
   STATUS            optional   
   DESCRIPTION " Contains a device specific error code. Each device POS should
   list what errors are logged to the error log and the meaning of
   each supported error code value"
::= { error10 2 }

-- 1.3.6.1.4.1.11.2.3.9.4.2.1.1.22.34.2   
warning34-code   OBJECT-TYPE
   SYNTAX          INTEGER    
   ACCESS           read-only    
   STATUS            optional   
   DESCRIPTION " Contains a device specific warning code. Each device POS should
   list what warnings are logged to the warning log and the
   meaning of each supported warning code value"
::= { warning34 2 }

-- 1.3.6.1.4.1.11.2.3.9.4.2.1.1.22.35.2   
warning35-code   OBJECT-TYPE
   SYNTAX          INTEGER    
   ACCESS           read-only    
   STATUS            optional   
   DESCRIPTION " Contains a device specific warning code. Each device POS should
   list what warnings are logged to the warning log and the
   meaning of each supported warning code value"
::= { warning35 2 }

-- 1.3.6.1.4.1.11.2.3.9.4.2.1.1.22.36.2   
warning36-code   OBJECT-TYPE
   SYNTAX          INTEGER    
   ACCESS           read-only    
   STATUS            optional   
   DESCRIPTION " Contains a device specific warning code. Each device POS should
   list what warnings are logged to the warning log and the
   meaning of each supported warning code value"
::= { warning36 2 }

-- 1.3.6.1.4.1.11.2.3.9.4.2.1.1.22.37.2   
warning37-code   OBJECT-TYPE
   SYNTAX          INTEGER    
   ACCESS           read-only    
   STATUS            optional   
   DESCRIPTION " Contains a device specific warning code. Each device POS should
   list what warnings are logged to the warning log and the
   meaning of each supported warning code value"
::= { warning37 2 }

-- 1.3.6.1.4.1.11.2.3.9.4.2.1.1.22.38.2   
warning38-code   OBJECT-TYPE
   SYNTAX          INTEGER    
   ACCESS           read-only    
   STATUS            optional   
   DESCRIPTION " Contains a device specific warning code. Each device POS should
   list what warnings are logged to the warning log and the
   meaning of each supported warning code value"
::= { warning38 2 }

-- 1.3.6.1.4.1.11.2.3.9.4.2.1.1.22.39.2   
warning39-code   OBJECT-TYPE
   SYNTAX          INTEGER    
   ACCESS           read-only    
   STATUS            optional   
   DESCRIPTION " Contains a device specific warning code. Each device POS should
   list what warnings are logged to the warning log and the
   meaning of each supported warning code value"
::= { warning39 2 }

-- 1.3.6.1.4.1.11.2.3.9.4.2.1.1.22.40.2   
warning40-code   OBJECT-TYPE
   SYNTAX          INTEGER    
   ACCESS           read-only    
   STATUS            optional   
   DESCRIPTION " Contains a device specific warning code. Each device POS should
   list what warnings are logged to the warning log and the
   meaning of each supported warning code value"
::= { warning40 2 }

-- 1.3.6.1.4.1.11.2.3.9.4.2.1.1.22.41.2   
warning41-code   OBJECT-TYPE
   SYNTAX          INTEGER    
   ACCESS           read-only    
   STATUS            optional   
   DESCRIPTION " Contains a device specific warning code. Each device POS should
   list what warnings are logged to the warning log and the
   meaning of each supported warning code value"
::= { warning41 2 }

-- 1.3.6.1.4.1.11.2.3.9.4.2.1.1.22.42.2   
warning42-code   OBJECT-TYPE
   SYNTAX          INTEGER    
   ACCESS           read-only    
   STATUS            optional   
   DESCRIPTION " Contains a device specific warning code. Each device POS should
   list what warnings are logged to the warning log and the
   meaning of each supported warning code value"
::= { warning42 2 }

-- 1.3.6.1.4.1.11.2.3.9.4.2.1.1.22.43.2   
warning43-code   OBJECT-TYPE
   SYNTAX          INTEGER    
   ACCESS           read-only    
   STATUS            optional   
   DESCRIPTION " Contains a device specific warning code. Each device POS should
   list what warnings are logged to the warning log and the
   meaning of each supported warning code value"
::= { warning43 2 }

-- 1.3.6.1.4.1.11.2.3.9.4.2.1.1.22.44.2   
warning44-code   OBJECT-TYPE
   SYNTAX          INTEGER    
   ACCESS           read-only    
   STATUS            optional   
   DESCRIPTION " Contains a device specific warning code. Each device POS should
   list what warnings are logged to the warning log and the
   meaning of each supported warning code value"
::= { warning44 2 }

-- 1.3.6.1.4.1.11.2.3.9.4.2.1.1.22.45.2   
warning45-code   OBJECT-TYPE
   SYNTAX          INTEGER    
   ACCESS           read-only    
   STATUS            optional   
   DESCRIPTION " Contains a device specific warning code. Each device POS should
   list what warnings are logged to the warning log and the
   meaning of each supported warning code value"
::= { warning45 2 }

-- 1.3.6.1.4.1.11.2.3.9.4.2.1.1.22.46.2   
warning46-code   OBJECT-TYPE
   SYNTAX          INTEGER    
   ACCESS           read-only    
   STATUS            optional   
   DESCRIPTION " Contains a device specific warning code. Each device POS should
   list what warnings are logged to the warning log and the
   meaning of each supported warning code value"
::= { warning46 2 }

-- 1.3.6.1.4.1.11.2.3.9.4.2.1.1.22.33.2   
warning33-code   OBJECT-TYPE
   SYNTAX          INTEGER    
   ACCESS           read-only    
   STATUS            optional   
   DESCRIPTION " Contains a device specific warning code. Each device POS should
   list what warnings are logged to the warning log and the
   meaning of each supported warning code value"
::= { warning33 2 }

-- 1.3.6.1.4.1.11.2.3.9.4.2.1.1.22.48.2   
warning48-code   OBJECT-TYPE
   SYNTAX          INTEGER    
   ACCESS           read-only    
   STATUS            optional   
   DESCRIPTION " Contains a device specific warning code. Each device POS should
   list what warnings are logged to the warning log and the
   meaning of each supported warning code value"
::= { warning48 2 }

-- 1.3.6.1.4.1.11.2.3.9.4.2.1.1.22.49.2   
warning49-code   OBJECT-TYPE
   SYNTAX          INTEGER    
   ACCESS           read-only    
   STATUS            optional   
   DESCRIPTION " Contains a device specific warning code. Each device POS should
   list what warnings are logged to the warning log and the
   meaning of each supported warning code value"
::= { warning49 2 }

-- 1.3.6.1.4.1.11.2.3.9.4.2.1.1.22.50.2   
warning50-code   OBJECT-TYPE
   SYNTAX          INTEGER    
   ACCESS           read-only    
   STATUS            optional   
   DESCRIPTION " Contains a device specific warning code. Each device POS should
   list what warnings are logged to the warning log and the
   meaning of each supported warning code value"
::= { warning50 2 }

-- 1.3.6.1.4.1.11.2.3.9.4.2.1.1.11.12.2   
error12-code   OBJECT-TYPE
   SYNTAX          INTEGER    
   ACCESS           read-only    
   STATUS            optional   
   DESCRIPTION " Contains a device specific error code. Each device POS should
   list what errors are logged to the error log and the meaning of
   each supported error code value"
::= { error12 2 }

-- 1.3.6.1.4.1.11.2.3.9.4.2.1.1.11.1.2   
error1-code   OBJECT-TYPE
   SYNTAX          INTEGER    
   ACCESS           read-only    
   STATUS            optional   
   DESCRIPTION " Contains a device specific error code. Each device POS should
   list what errors are logged to the error log and the meaning of
   each supported error code value"
::= { error1 2 }

-- 1.3.6.1.4.1.11.2.3.9.4.2.1.1.11.2.2   
error2-code   OBJECT-TYPE
   SYNTAX          INTEGER    
   ACCESS           read-only    
   STATUS            optional   
   DESCRIPTION " Contains a device specific error code. Each device POS should
   list what errors are logged to the error log and the meaning of
   each supported error code value"
::= { error2 2 }

-- 1.3.6.1.4.1.11.2.3.9.4.2.1.1.11.3.2   
error3-code   OBJECT-TYPE
   SYNTAX          INTEGER    
   ACCESS           read-only    
   STATUS            optional   
   DESCRIPTION " Contains a device specific error code. Each device POS should
   list what errors are logged to the error log and the meaning of
   each supported error code value"
::= { error3 2 }

-- 1.3.6.1.4.1.11.2.3.9.4.2.1.1.11.4.2   
error4-code   OBJECT-TYPE
   SYNTAX          INTEGER    
   ACCESS           read-only    
   STATUS            optional   
   DESCRIPTION " Contains a device specific error code. Each device POS should
   list what errors are logged to the error log and the meaning of
   each supported error code value"
::= { error4 2 }

-- 1.3.6.1.4.1.11.2.3.9.4.2.1.1.11.5.2   
error5-code   OBJECT-TYPE
   SYNTAX          INTEGER    
   ACCESS           read-only    
   STATUS            optional   
   DESCRIPTION " Contains a device specific error code. Each device POS should
   list what errors are logged to the error log and the meaning of
   each supported error code value"
::= { error5 2 }

-- 1.3.6.1.4.1.11.2.3.9.4.2.1.1.11.6.2   
error6-code   OBJECT-TYPE
   SYNTAX          INTEGER    
   ACCESS           read-only    
   STATUS            optional   
   DESCRIPTION " Contains a device specific error code. Each device POS should
   list what errors are logged to the error log and the meaning of
   each supported error code value"
::= { error6 2 }

-- 1.3.6.1.4.1.11.2.3.9.4.2.1.1.11.7.2   
error7-code   OBJECT-TYPE
   SYNTAX          INTEGER    
   ACCESS           read-only    
   STATUS            optional   
   DESCRIPTION " Contains a device specific error code. Each device POS should
   list what errors are logged to the error log and the meaning of
   each supported error code value"
::= { error7 2 }

-- 1.3.6.1.4.1.11.2.3.9.4.2.1.1.11.8.2   
error8-code   OBJECT-TYPE
   SYNTAX          INTEGER    
   ACCESS           read-only    
   STATUS            optional   
   DESCRIPTION " Contains a device specific error code. Each device POS should
   list what errors are logged to the error log and the meaning of
   each supported error code value"
::= { error8 2 }

-- 1.3.6.1.4.1.11.2.3.9.4.2.1.1.11.9.2   
error9-code   OBJECT-TYPE
   SYNTAX          INTEGER    
   ACCESS           read-only    
   STATUS            optional   
   DESCRIPTION " Contains a device specific error code. Each device POS should
   list what errors are logged to the error log and the meaning of
   each supported error code value"
::= { error9 2 }

-- 1.3.6.1.4.1.11.2.3.9.4.2.1.1.11.13.3   
error13-date-time   OBJECT-TYPE
   SYNTAX          OCTET STRING    
   ACCESS           read-only    
   STATUS            optional   
   DESCRIPTION " This item contains the date and the time at which an error
   occurred. The values returned will be in hexadecimal. If the
   date is 2004-Jul-13 and the time is 03:15 a.m., we get 04 07 0d
   03 0f where, \\ 
   04 (hex) - corresponds to the year 2004. \\ 
   07 (hex) - corresponds to month, 07 \\ 
   0d (hex) - corresponds to date, 13 \\ 
   03 (hex) - corresponds to hour, 3 a.m. \\ 
   0f (hex) - corresponds to min, 15. \\ "
::= { error13 3 }

-- 1.3.6.1.4.1.11.2.3.9.4.2.1.1.11.14.3   
error14-date-time   OBJECT-TYPE
   SYNTAX          OCTET STRING    
   ACCESS           read-only    
   STATUS            optional   
   DESCRIPTION " This item contains the date and the time at which an error
   occurred. The values returned will be in hexadecimal. If the
   date is 2004-Jul-13 and the time is 03:15 a.m., we get 04 07 0d
       03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { error14 3 }

-- 1.3.6.1.4.1.11.2.3.9.4.2.1.1.11.15.3   
error15-date-time   OBJECT-TYPE
   SYNTAX          OCTET STRING    
   ACCESS           read-only    
   STATUS            optional   
   DESCRIPTION " This item contains the date and the time at which an error
   occurred. The values returned will be in hexadecimal. If the
   date is 2004-Jul-13 and the time is 03:15 a.m., we get 04 07 0d
       03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { error15 3 }

-- 1.3.6.1.4.1.11.2.3.9.4.2.1.1.11.16.3   
error16-date-time   OBJECT-TYPE
   SYNTAX          OCTET STRING    
   ACCESS           read-only    
   STATUS            optional   
   DESCRIPTION " This item contains the date and the time at which an error
   occurred. The values returned will be in hexadecimal. If the
   date is 2004-Jul-13 and the time is 03:15 a.m., we get 04 07 0d
       03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { error16 3 }

-- 1.3.6.1.4.1.11.2.3.9.4.2.1.1.11.17.3   
error17-date-time   OBJECT-TYPE
   SYNTAX          OCTET STRING    
   ACCESS           read-only    
   STATUS            optional   
   DESCRIPTION " This item contains the date and the time at which an error
   occurred. The values returned will be in hexadecimal. If the
   date is 2004-Jul-13 and the time is 03:15 a.m., we get 04 07 0d
       03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { error17 3 }

-- 1.3.6.1.4.1.11.2.3.9.4.2.1.1.11.18.3   
error18-date-time   OBJECT-TYPE
   SYNTAX          OCTET STRING    
   ACCESS           read-only    
   STATUS            optional   
   DESCRIPTION " This item contains the date and the time at which an error
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { error18 3 }

-- 1.3.6.1.4.1.11.2.3.9.4.2.1.1.11.19.3   
error19-date-time   OBJECT-TYPE
   SYNTAX          OCTET STRING    
   ACCESS           read-only    
   STATUS            optional   
   DESCRIPTION " This item contains the date and the time at which an error
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { error19 3 }

-- 1.3.6.1.4.1.11.2.3.9.4.2.1.1.11.20.3   
error20-date-time   OBJECT-TYPE
   SYNTAX          OCTET STRING    
   ACCESS           read-only    
   STATUS            optional   
   DESCRIPTION " This item contains the date and the time at which an error
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { error20 3 }

-- 1.3.6.1.4.1.11.2.3.9.4.2.1.1.11.21.3   
error21-date-time   OBJECT-TYPE
   SYNTAX          OCTET STRING    
   ACCESS           read-only    
   STATUS            optional   
   DESCRIPTION " This item contains the date and the time at which an error
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { error21 3 }

-- 1.3.6.1.4.1.11.2.3.9.4.2.1.1.11.22.3   
error22-date-time   OBJECT-TYPE
   SYNTAX          OCTET STRING    
   ACCESS           read-only    
   STATUS            optional   
   DESCRIPTION " This item contains the date and the time at which an error
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { error22 3 }

-- 1.3.6.1.4.1.11.2.3.9.4.2.1.1.11.23.3   
error23-date-time   OBJECT-TYPE
   SYNTAX          OCTET STRING    
   ACCESS           read-only    
   STATUS            optional   
   DESCRIPTION " This item contains the date and the time at which an error
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { error23 3 }

-- 1.3.6.1.4.1.11.2.3.9.4.2.1.1.11.24.3   
error24-date-time   OBJECT-TYPE
   SYNTAX          OCTET STRING    
   ACCESS           read-only    
   STATUS            optional   
   DESCRIPTION " This item contains the date and the time at which an error
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { error24 3 }

-- 1.3.6.1.4.1.11.2.3.9.4.2.1.1.11.25.3   
error25-date-time   OBJECT-TYPE
   SYNTAX          OCTET STRING    
   ACCESS           read-only    
   STATUS            optional   
   DESCRIPTION " This item contains the date and the time at which an error
   occurred. The values returned will be in hexadecimal. If the
   date is 2004-Jul-13 and the time is 03:15 a.m., we get 04 07 0d
   03 0f where, \\ 
   04 (hex) - corresponds to the year 2004. \\ 
   07 (hex) - corresponds to month, 07 \\ 
   0d (hex) - corresponds to date, 13 \\ 
   03 (hex) - corresponds to hour, 3 a.m. \\ 
   0f (hex) - corresponds to min, 15. \\"
::= { error25 3 }

-- 1.3.6.1.4.1.11.2.3.9.4.2.1.1.11.26.3   
error26-date-time   OBJECT-TYPE
   SYNTAX          OCTET STRING    
   ACCESS           read-only    
   STATUS            optional   
   DESCRIPTION " This item contains the date and the time at which an error
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { error26 3 }

-- 1.3.6.1.4.1.11.2.3.9.4.2.1.1.11.27.3   
error27-date-time   OBJECT-TYPE
   SYNTAX          OCTET STRING    
   ACCESS           read-only    
   STATUS            optional   
   DESCRIPTION " This item contains the date and the time at which an error
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { error27 3 }

-- 1.3.6.1.4.1.11.2.3.9.4.2.1.1.11.28.3   
error28-date-time   OBJECT-TYPE
   SYNTAX          OCTET STRING    
   ACCESS           read-only    
   STATUS            optional   
   DESCRIPTION " This item contains the date and the time at which an error
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { error28 3 }

-- 1.3.6.1.4.1.11.2.3.9.4.2.1.1.11.29.3   
error29-date-time   OBJECT-TYPE
   SYNTAX          OCTET STRING    
   ACCESS           read-only    
   STATUS            optional   
   DESCRIPTION " This item contains the date and the time at which an error
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { error29 3 }

-- 1.3.6.1.4.1.11.2.3.9.4.2.1.1.11.30.3   
error30-date-time   OBJECT-TYPE
   SYNTAX          OCTET STRING    
   ACCESS           read-only    
   STATUS            optional   
   DESCRIPTION " This item contains the date and the time at which an error
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { error30 3 }

-- 1.3.6.1.4.1.11.2.3.9.4.2.1.1.11.31.3   
error31-date-time   OBJECT-TYPE
   SYNTAX          OCTET STRING    
   ACCESS           read-only    
   STATUS            optional   
   DESCRIPTION " This item contains the date and the time at which an error
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { error31 3 }

-- 1.3.6.1.4.1.11.2.3.9.4.2.1.1.11.32.3   
error32-date-time   OBJECT-TYPE
   SYNTAX          OCTET STRING    
   ACCESS           read-only    
   STATUS            optional   
   DESCRIPTION " This item contains the date and the time at which an error
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { error32 3 }

-- 1.3.6.1.4.1.11.2.3.9.4.2.1.1.11.33.3   
error33-date-time   OBJECT-TYPE
   SYNTAX          OCTET STRING    
   ACCESS           read-only    
   STATUS            optional   
   DESCRIPTION " This item contains the date and the time at which an error
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { error33 3 }

-- 1.3.6.1.4.1.11.2.3.9.4.2.1.1.11.34.3   
error34-date-time   OBJECT-TYPE
   SYNTAX          OCTET STRING    
   ACCESS           read-only    
   STATUS            optional   
   DESCRIPTION " This item contains the date and the time at which an error
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { error34 3 }

-- 1.3.6.1.4.1.11.2.3.9.4.2.1.1.11.35.3   
error35-date-time   OBJECT-TYPE
   SYNTAX          OCTET STRING    
   ACCESS           read-only    
   STATUS            optional   
   DESCRIPTION " This item contains the date and the time at which an error
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { error35 3 }

-- 1.3.6.1.4.1.11.2.3.9.4.2.1.1.11.36.3   
error36-date-time   OBJECT-TYPE
   SYNTAX          OCTET STRING    
   ACCESS           read-only    
   STATUS            optional   
   DESCRIPTION " This item contains the date and the time at which an error
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { error36 3 }

-- 1.3.6.1.4.1.11.2.3.9.4.2.1.1.11.37.3   
error37-date-time   OBJECT-TYPE
   SYNTAX          OCTET STRING    
   ACCESS           read-only    
   STATUS            optional   
   DESCRIPTION " This item contains the date and the time at which an error
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { error37 3 }

-- 1.3.6.1.4.1.11.2.3.9.4.2.1.1.11.38.3   
error38-date-time   OBJECT-TYPE
   SYNTAX          OCTET STRING    
   ACCESS           read-only    
   STATUS            optional   
   DESCRIPTION " This item contains the date and the time at which an error
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { error38 3 }

-- 1.3.6.1.4.1.11.2.3.9.4.2.1.1.11.39.3   
error39-date-time   OBJECT-TYPE
   SYNTAX          OCTET STRING    
   ACCESS           read-only    
   STATUS            optional   
   DESCRIPTION " This item contains the date and the time at which an error
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { error39 3 }

-- 1.3.6.1.4.1.11.2.3.9.4.2.1.1.11.40.3   
error40-date-time   OBJECT-TYPE
   SYNTAX          OCTET STRING    
   ACCESS           read-only    
   STATUS            optional   
   DESCRIPTION " This item contains the date and the time at which an error
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { error40 3 }

-- 1.3.6.1.4.1.11.2.3.9.4.2.1.1.11.41.3   
error41-date-time   OBJECT-TYPE
   SYNTAX          OCTET STRING    
   ACCESS           read-only    
   STATUS            optional   
   DESCRIPTION " This item contains the date and the time at which an error
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { error41 3 }

-- 1.3.6.1.4.1.11.2.3.9.4.2.1.1.11.42.3   
error42-date-time   OBJECT-TYPE
   SYNTAX          OCTET STRING    
   ACCESS           read-only    
   STATUS            optional   
   DESCRIPTION " This item contains the date and the time at which an error
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { error42 3 }

-- 1.3.6.1.4.1.11.2.3.9.4.2.1.1.11.43.3   
error43-date-time   OBJECT-TYPE
   SYNTAX          OCTET STRING    
   ACCESS           read-only    
   STATUS            optional   
   DESCRIPTION " This item contains the date and the time at which an error
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { error43 3 }

-- 1.3.6.1.4.1.11.2.3.9.4.2.1.1.11.44.3   
error44-date-time   OBJECT-TYPE
   SYNTAX          OCTET STRING    
   ACCESS           read-only    
   STATUS            optional   
   DESCRIPTION " This item contains the date and the time at which an error
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { error44 3 }

-- 1.3.6.1.4.1.11.2.3.9.4.2.1.1.11.45.3   
error45-date-time   OBJECT-TYPE
   SYNTAX          OCTET STRING    
   ACCESS           read-only    
   STATUS            optional   
   DESCRIPTION " This item contains the date and the time at which an error
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { error45 3 }

-- 1.3.6.1.4.1.11.2.3.9.4.2.1.1.11.46.3   
error46-date-time   OBJECT-TYPE
   SYNTAX          OCTET STRING    
   ACCESS           read-only    
   STATUS            optional   
   DESCRIPTION " This item contains the date and the time at which an error
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { error46 3 }

-- 1.3.6.1.4.1.11.2.3.9.4.2.1.1.11.47.3   
error47-date-time   OBJECT-TYPE
   SYNTAX          OCTET STRING    
   ACCESS           read-only    
   STATUS            optional   
   DESCRIPTION " This item contains the date and the time at which an error
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { error47 3 }

-- 1.3.6.1.4.1.11.2.3.9.4.2.1.1.11.48.3   
error48-date-time   OBJECT-TYPE
   SYNTAX          OCTET STRING    
   ACCESS           read-only    
   STATUS            optional   
   DESCRIPTION " This item contains the date and the time at which an error
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { error48 3 }

-- 1.3.6.1.4.1.11.2.3.9.4.2.1.1.11.49.3   
error49-date-time   OBJECT-TYPE
   SYNTAX          OCTET STRING    
   ACCESS           read-only    
   STATUS            optional   
   DESCRIPTION " This item contains the date and the time at which an error
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { error49 3 }

-- 1.3.6.1.4.1.11.2.3.9.4.2.1.1.11.50.3   
error50-date-time   OBJECT-TYPE
   SYNTAX          OCTET STRING    
   ACCESS           read-only    
   STATUS            optional   
   DESCRIPTION " This item contains the date and the time at which an error
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { error50 3 }

-- 1.3.6.1.4.1.11.2.3.9.4.2.1.1.22.1.3   
warning1-date-time   OBJECT-TYPE
   SYNTAX          OCTET STRING    
   ACCESS           read-only    
   STATUS            optional   
   DESCRIPTION " This item contains the date and the time at which an warning
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { warning1 3 }

-- 1.3.6.1.4.1.11.2.3.9.4.2.1.1.22.2.3   
warning2-date-time   OBJECT-TYPE
   SYNTAX          OCTET STRING    
   ACCESS           read-only    
   STATUS            optional   
   DESCRIPTION " This item contains the date and the time at which an warning
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { warning2 3 }

-- 1.3.6.1.4.1.11.2.3.9.4.2.1.1.22.3.3   
warning3-date-time   OBJECT-TYPE
   SYNTAX          OCTET STRING    
   ACCESS           read-only    
   STATUS            optional   
   DESCRIPTION " This item contains the date and the time at which an warning
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { warning3 3 }

-- 1.3.6.1.4.1.11.2.3.9.4.2.1.1.22.4.3   
warning4-date-time   OBJECT-TYPE
   SYNTAX          OCTET STRING    
   ACCESS           read-only    
   STATUS            optional   
   DESCRIPTION " This item contains the date and the time at which an warning
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { warning4 3 }

-- 1.3.6.1.4.1.11.2.3.9.4.2.1.1.22.5.3   
warning5-date-time   OBJECT-TYPE
   SYNTAX          OCTET STRING    
   ACCESS           read-only    
   STATUS            optional   
   DESCRIPTION " This item contains the date and the time at which an warning
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { warning5 3 }

-- 1.3.6.1.4.1.11.2.3.9.4.2.1.1.22.6.3   
warning6-date-time   OBJECT-TYPE
   SYNTAX          OCTET STRING    
   ACCESS           read-only    
   STATUS            optional   
   DESCRIPTION " This item contains the date and the time at which an warning
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { warning6 3 }

-- 1.3.6.1.4.1.11.2.3.9.4.2.1.1.22.7.3   
warning7-date-time   OBJECT-TYPE
   SYNTAX          OCTET STRING    
   ACCESS           read-only    
   STATUS            optional   
   DESCRIPTION " This item contains the date and the time at which an warning
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { warning7 3 }

-- 1.3.6.1.4.1.11.2.3.9.4.2.1.1.22.8.3   
warning8-date-time   OBJECT-TYPE
   SYNTAX          OCTET STRING    
   ACCESS           read-only    
   STATUS            optional   
   DESCRIPTION " This item contains the date and the time at which an warning
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { warning8 3 }

-- 1.3.6.1.4.1.11.2.3.9.4.2.1.1.22.9.3   
warning9-date-time   OBJECT-TYPE
   SYNTAX          OCTET STRING    
   ACCESS           read-only    
   STATUS            optional   
   DESCRIPTION " This item contains the date and the time at which an warning
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { warning9 3 }

-- 1.3.6.1.4.1.11.2.3.9.4.2.1.1.22.10.3   
warning10-date-time   OBJECT-TYPE
   SYNTAX          OCTET STRING    
   ACCESS           read-only    
   STATUS            optional   
   DESCRIPTION " This item contains the date and the time at which an warning
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { warning10 3 }

-- 1.3.6.1.4.1.11.2.3.9.4.2.1.1.22.11.3   
warning11-date-time   OBJECT-TYPE
   SYNTAX          OCTET STRING    
   ACCESS           read-only    
   STATUS            optional   
   DESCRIPTION " This item contains the date and the time at which an warning
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { warning11 3 }

-- 1.3.6.1.4.1.11.2.3.9.4.2.1.1.22.12.3   
warning12-date-time   OBJECT-TYPE
   SYNTAX          OCTET STRING    
   ACCESS           read-only    
   STATUS            optional   
   DESCRIPTION " This item contains the date and the time at which an warning
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { warning12 3 }

-- 1.3.6.1.4.1.11.2.3.9.4.2.1.1.22.13.3   
warning13-date-time   OBJECT-TYPE
   SYNTAX          OCTET STRING    
   ACCESS           read-only    
   STATUS            optional   
   DESCRIPTION " This item contains the date and the time at which an warning
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { warning13 3 }

-- 1.3.6.1.4.1.11.2.3.9.4.2.1.1.22.14.3   
warning14-date-time   OBJECT-TYPE
   SYNTAX          OCTET STRING    
   ACCESS           read-only    
   STATUS            optional   
   DESCRIPTION " This item contains the date and the time at which an warning
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { warning14 3 }

-- 1.3.6.1.4.1.11.2.3.9.4.2.1.1.22.15.3   
warning15-date-time   OBJECT-TYPE
   SYNTAX          OCTET STRING    
   ACCESS           read-only    
   STATUS            optional   
   DESCRIPTION " This item contains the date and the time at which an warning
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { warning15 3 }

-- 1.3.6.1.4.1.11.2.3.9.4.2.1.1.22.16.3   
warning16-date-time   OBJECT-TYPE
   SYNTAX          OCTET STRING    
   ACCESS           read-only    
   STATUS            optional   
   DESCRIPTION " This item contains the date and the time at which an warning
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { warning16 3 }

-- 1.3.6.1.4.1.11.2.3.9.4.2.1.1.22.17.3   
warning17-date-time   OBJECT-TYPE
   SYNTAX          OCTET STRING    
   ACCESS           read-only    
   STATUS            optional   
   DESCRIPTION " This item contains the date and the time at which an warning
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { warning17 3 }

-- 1.3.6.1.4.1.11.2.3.9.4.2.1.1.22.18.3   
warning18-date-time   OBJECT-TYPE
   SYNTAX          OCTET STRING    
   ACCESS           read-only    
   STATUS            optional   
   DESCRIPTION " This item contains the date and the time at which an warning
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { warning18 3 }

-- 1.3.6.1.4.1.11.2.3.9.4.2.1.1.22.19.3   
warning19-date-time   OBJECT-TYPE
   SYNTAX          OCTET STRING    
   ACCESS           read-only    
   STATUS            optional   
   DESCRIPTION " This item contains the date and the time at which an warning
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { warning19 3 }

-- 1.3.6.1.4.1.11.2.3.9.4.2.1.1.22.20.3   
warning20-date-time   OBJECT-TYPE
   SYNTAX          OCTET STRING    
   ACCESS           read-only    
   STATUS            optional   
   DESCRIPTION " This item contains the date and the time at which an warning
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { warning20 3 }

-- 1.3.6.1.4.1.11.2.3.9.4.2.1.1.22.21.3   
warning21-date-time   OBJECT-TYPE
   SYNTAX          OCTET STRING    
   ACCESS           read-only    
   STATUS            optional   
   DESCRIPTION " This item contains the date and the time at which an warning
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { warning21 3 }

-- 1.3.6.1.4.1.11.2.3.9.4.2.1.1.22.22.3   
warning22-date-time   OBJECT-TYPE
   SYNTAX          OCTET STRING    
   ACCESS           read-only    
   STATUS            optional   
   DESCRIPTION " This item contains the date and the time at which an warning
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { warning22 3 }

-- 1.3.6.1.4.1.11.2.3.9.4.2.1.1.22.23.3   
warning23-date-time   OBJECT-TYPE
   SYNTAX          OCTET STRING    
   ACCESS           read-only    
   STATUS            optional   
   DESCRIPTION " This item contains the date and the time at which an warning
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { warning23 3 }

-- 1.3.6.1.4.1.11.2.3.9.4.2.1.1.22.24.3   
warning24-date-time   OBJECT-TYPE
   SYNTAX          OCTET STRING    
   ACCESS           read-only    
   STATUS            optional   
   DESCRIPTION " This item contains the date and the time at which an warning
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { warning24 3 }

-- 1.3.6.1.4.1.11.2.3.9.4.2.1.1.22.25.3   
warning25-date-time   OBJECT-TYPE
   SYNTAX          OCTET STRING    
   ACCESS           read-only    
   STATUS            optional   
   DESCRIPTION " This item contains the date and the time at which an warning
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { warning25 3 }

-- 1.3.6.1.4.1.11.2.3.9.4.2.1.1.22.26.3   
warning26-date-time   OBJECT-TYPE
   SYNTAX          OCTET STRING    
   ACCESS           read-only    
   STATUS            optional   
   DESCRIPTION " This item contains the date and the time at which an warning
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { warning26 3 }

-- 1.3.6.1.4.1.11.2.3.9.4.2.1.1.22.27.3   
warning27-date-time   OBJECT-TYPE
   SYNTAX          OCTET STRING    
   ACCESS           read-only    
   STATUS            optional   
   DESCRIPTION " This item contains the date and the time at which an warning
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { warning27 3 }

-- 1.3.6.1.4.1.11.2.3.9.4.2.1.1.22.28.3   
warning28-date-time   OBJECT-TYPE
   SYNTAX          OCTET STRING    
   ACCESS           read-only    
   STATUS            optional   
   DESCRIPTION " This item contains the date and the time at which an warning
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { warning28 3 }

-- 1.3.6.1.4.1.11.2.3.9.4.2.1.1.22.29.3   
warning29-date-time   OBJECT-TYPE
   SYNTAX          OCTET STRING    
   ACCESS           read-only    
   STATUS            optional   
   DESCRIPTION " This item contains the date and the time at which an warning
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { warning29 3 }

-- 1.3.6.1.4.1.11.2.3.9.4.2.1.1.22.30.3   
warning30-date-time   OBJECT-TYPE
   SYNTAX          OCTET STRING    
   ACCESS           read-only    
   STATUS            optional   
   DESCRIPTION " This item contains the date and the time at which an warning
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { warning30 3 }

-- 1.3.6.1.4.1.11.2.3.9.4.2.1.1.22.31.3   
warning31-date-time   OBJECT-TYPE
   SYNTAX          OCTET STRING    
   ACCESS           read-only    
   STATUS            optional   
   DESCRIPTION " This item contains the date and the time at which an warning
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { warning31 3 }

-- 1.3.6.1.4.1.11.2.3.9.4.2.1.1.22.32.3   
warning32-date-time   OBJECT-TYPE
   SYNTAX          OCTET STRING    
   ACCESS           read-only    
   STATUS            optional   
   DESCRIPTION " This item contains the date and the time at which an warning
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { warning32 3 }

-- 1.3.6.1.4.1.11.2.3.9.4.2.1.1.22.33.3   
warning33-date-time   OBJECT-TYPE
   SYNTAX          OCTET STRING    
   ACCESS           read-only    
   STATUS            optional   
   DESCRIPTION " This item contains the date and the time at which an warning
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { warning33 3 }

-- 1.3.6.1.4.1.11.2.3.9.4.2.1.1.22.34.3   
warning34-date-time   OBJECT-TYPE
   SYNTAX          OCTET STRING    
   ACCESS           read-only    
   STATUS            optional   
   DESCRIPTION " This item contains the date and the time at which an warning
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { warning34 3 }

-- 1.3.6.1.4.1.11.2.3.9.4.2.1.1.22.35.3   
warning35-date-time   OBJECT-TYPE
   SYNTAX          OCTET STRING    
   ACCESS           read-only    
   STATUS            optional   
   DESCRIPTION " This item contains the date and the time at which an warning
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { warning35 3 }

-- 1.3.6.1.4.1.11.2.3.9.4.2.1.1.22.36.3   
warning36-date-time   OBJECT-TYPE
   SYNTAX          OCTET STRING    
   ACCESS           read-only    
   STATUS            optional   
   DESCRIPTION " This item contains the date and the time at which an warning
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { warning36 3 }

-- 1.3.6.1.4.1.11.2.3.9.4.2.1.1.22.37.3   
warning37-date-time   OBJECT-TYPE
   SYNTAX          OCTET STRING    
   ACCESS           read-only    
   STATUS            optional   
   DESCRIPTION " This item contains the date and the time at which an warning
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { warning37 3 }

-- 1.3.6.1.4.1.11.2.3.9.4.2.1.1.22.38.3   
warning38-date-time   OBJECT-TYPE
   SYNTAX          OCTET STRING    
   ACCESS           read-only    
   STATUS            optional   
   DESCRIPTION " This item contains the date and the time at which an warning
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { warning38 3 }

-- 1.3.6.1.4.1.11.2.3.9.4.2.1.1.22.39.3   
warning39-date-time   OBJECT-TYPE
   SYNTAX          OCTET STRING    
   ACCESS           read-only    
   STATUS            optional   
   DESCRIPTION " This item contains the date and the time at which an warning
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { warning39 3 }

-- 1.3.6.1.4.1.11.2.3.9.4.2.1.1.11.1.3   
error1-date-time   OBJECT-TYPE
   SYNTAX          OCTET STRING    
   ACCESS           read-only    
   STATUS            optional   
   DESCRIPTION " This item contains the date and the time at which an error
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { error1 3 }

-- 1.3.6.1.4.1.11.2.3.9.4.2.1.1.22.41.3   
warning41-date-time   OBJECT-TYPE
   SYNTAX          OCTET STRING    
   ACCESS           read-only    
   STATUS            optional   
   DESCRIPTION " This item contains the date and the time at which an warning
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { warning41 3 }

-- 1.3.6.1.4.1.11.2.3.9.4.2.1.1.22.42.3   
warning42-date-time   OBJECT-TYPE
   SYNTAX          OCTET STRING    
   ACCESS           read-only    
   STATUS            optional   
   DESCRIPTION " This item contains the date and the time at which an warning
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { warning42 3 }

-- 1.3.6.1.4.1.11.2.3.9.4.2.1.1.22.43.3   
warning43-date-time   OBJECT-TYPE
   SYNTAX          OCTET STRING    
   ACCESS           read-only    
   STATUS            optional   
   DESCRIPTION " This item contains the date and the time at which an warning
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { warning43 3 }

-- 1.3.6.1.4.1.11.2.3.9.4.2.1.1.22.44.3   
warning44-date-time   OBJECT-TYPE
   SYNTAX          OCTET STRING    
   ACCESS           read-only    
   STATUS            optional   
   DESCRIPTION " This item contains the date and the time at which an warning
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { warning44 3 }

-- 1.3.6.1.4.1.11.2.3.9.4.2.1.1.22.45.3   
warning45-date-time   OBJECT-TYPE
   SYNTAX          OCTET STRING    
   ACCESS           read-only    
   STATUS            optional   
   DESCRIPTION " This item contains the date and the time at which an warning
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { warning45 3 }

-- 1.3.6.1.4.1.11.2.3.9.4.2.1.1.22.46.3   
warning46-date-time   OBJECT-TYPE
   SYNTAX          OCTET STRING    
   ACCESS           read-only    
   STATUS            optional   
   DESCRIPTION " This item contains the date and the time at which an warning
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { warning46 3 }

-- 1.3.6.1.4.1.11.2.3.9.4.2.1.1.22.47.3   
warning47-date-time   OBJECT-TYPE
   SYNTAX          OCTET STRING    
   ACCESS           read-only    
   STATUS            optional   
   DESCRIPTION " This item contains the date and the time at which an warning
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { warning47 3 }

-- 1.3.6.1.4.1.11.2.3.9.4.2.1.1.22.48.3   
warning48-date-time   OBJECT-TYPE
   SYNTAX          OCTET STRING    
   ACCESS           read-only    
   STATUS            optional   
   DESCRIPTION " This item contains the date and the time at which an warning
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { warning48 3 }

-- 1.3.6.1.4.1.11.2.3.9.4.2.1.1.22.49.3   
warning49-date-time   OBJECT-TYPE
   SYNTAX          OCTET STRING    
   ACCESS           read-only    
   STATUS            optional   
   DESCRIPTION " This item contains the date and the time at which an warning
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { warning49 3 }

-- 1.3.6.1.4.1.11.2.3.9.4.2.1.1.22.50.3   
warning50-date-time   OBJECT-TYPE
   SYNTAX          OCTET STRING    
   ACCESS           read-only    
   STATUS            optional   
   DESCRIPTION " This item contains the date and the time at which an warning
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { warning50 3 }

-- 1.3.6.1.4.1.11.2.3.9.4.2.1.1.11.2.3   
error2-date-time   OBJECT-TYPE
   SYNTAX          OCTET STRING    
   ACCESS           read-only    
   STATUS            optional   
   DESCRIPTION " This item contains the date and the time at which an error
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { error2 3 }

-- 1.3.6.1.4.1.11.2.3.9.4.2.1.1.22.40.3   
warning40-date-time   OBJECT-TYPE
   SYNTAX          OCTET STRING    
   ACCESS           read-only    
   STATUS            optional   
   DESCRIPTION " This item contains the date and the time at which an warning
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { warning40 3 }

-- 1.3.6.1.4.1.11.2.3.9.4.2.1.1.11.3.3   
error3-date-time   OBJECT-TYPE
   SYNTAX          OCTET STRING    
   ACCESS           read-only    
   STATUS            optional   
   DESCRIPTION " This item contains the date and the time at which an error
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { error3 3 }

-- 1.3.6.1.4.1.11.2.3.9.4.2.1.1.11.4.3   
error4-date-time   OBJECT-TYPE
   SYNTAX          OCTET STRING    
   ACCESS           read-only    
   STATUS            optional   
   DESCRIPTION " This item contains the date and the time at which an error
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { error4 3 }

-- 1.3.6.1.4.1.11.2.3.9.4.2.1.1.11.5.3   
error5-date-time   OBJECT-TYPE
   SYNTAX          OCTET STRING    
   ACCESS           read-only    
   STATUS            optional   
   DESCRIPTION " This item contains the date and the time at which an error
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { error5 3 }

-- 1.3.6.1.4.1.11.2.3.9.4.2.1.1.11.6.3   
error6-date-time   OBJECT-TYPE
   SYNTAX          OCTET STRING    
   ACCESS           read-only    
   STATUS            optional   
   DESCRIPTION " This item contains the date and the time at which an error
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { error6 3 }

-- 1.3.6.1.4.1.11.2.3.9.4.2.1.1.11.7.3   
error7-date-time   OBJECT-TYPE
   SYNTAX          OCTET STRING    
   ACCESS           read-only    
   STATUS            optional   
   DESCRIPTION " This item contains the date and the time at which an error
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { error7 3 }

-- 1.3.6.1.4.1.11.2.3.9.4.2.1.1.11.8.3   
error8-date-time   OBJECT-TYPE
   SYNTAX          OCTET STRING    
   ACCESS           read-only    
   STATUS            optional   
   DESCRIPTION " This item contains the date and the time at which an error
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { error8 3 }

-- 1.3.6.1.4.1.11.2.3.9.4.2.1.1.11.9.3   
error9-date-time   OBJECT-TYPE
   SYNTAX          OCTET STRING    
   ACCESS           read-only    
   STATUS            optional   
   DESCRIPTION " This item contains the date and the time at which an error
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { error9 3 }

-- 1.3.6.1.4.1.11.2.3.9.4.2.1.1.11.10.3   
error10-date-time   OBJECT-TYPE
   SYNTAX          OCTET STRING    
   ACCESS           read-only    
   STATUS            optional   
   DESCRIPTION " This item contains the date and the time at which an error
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { error10 3 }

-- 1.3.6.1.4.1.11.2.3.9.4.2.1.1.11.11.3   
error11-date-time   OBJECT-TYPE
   SYNTAX          OCTET STRING    
   ACCESS           read-only    
   STATUS            optional   
   DESCRIPTION " This item contains the date and the time at which an error
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { error11 3 }

-- 1.3.6.1.4.1.11.2.3.9.4.2.1.1.11.12.3   
error12-date-time   OBJECT-TYPE
   SYNTAX          OCTET STRING    
   ACCESS           read-only    
   STATUS            optional   
   DESCRIPTION " This item contains the date and the time at which an error
   occurred. The values returned will be in hexadecimal. If the
   date is 2004-Jul-13 and the time is 03:15 a.m., we get 04 07 0d
   03 0f where, \\ 
       04 (hex) - corresponds to the year 2004. \\ 
       07 (hex) - corresponds to month, 07 \\ 
       0d (hex) - corresponds to date, 13 \\ 
       03 (hex) - corresponds to hour, 3 a.m. \\ 
       0f (hex) - corresponds to min, 15. \\"
::= { error12 3 }

-- 1.3.6.1.4.1.11.2.3.9.4.2.1.1.1.71   
order-cartridge   OBJECT-TYPE
   SYNTAX          INTEGER {
                       eOff(1),
                      eOn(2)
               }   
   ACCESS           read-write    
   STATUS            optional   
   DESCRIPTION " Used to enable/disable the supplies status message that is
   shown when the supply reaches low"
::= { settings-system 71 }

-- 1.3.6.1.4.1.11.2.3.9.4.2.1.1.6.1.1   
clearable-warning   OBJECT-TYPE
   SYNTAX          INTEGER {
                       eOff(1),
                      eOn(2),
                      eJob(3)
               }   
   ACCESS           read-write    
   STATUS            optional   
   DESCRIPTION " Returns or controls how the device will track clearable
   warnings. A clearable warning indicates a transient event in
   the device. The device will continue after the transient event
   occurs. If CLEARABLE-WARNING is eOff, the device does not track
   clearable warnings. If CLEARABLE-WARNING is eOn, all clearable
   warnings will be tracked until cleared (acknowledged). If
   CLEARABLE-WARNING is eJob, a clearable warning generated due to
   an event that occurs because of the print job being processed
   will be automatically cleared when the device has finished
   processing the job. Example clearable warning events include
   the device altering resolution or page protection due to memory
   constraints. The POS will document what transient events are
   treated as clearable warnings"
::= { settings-job 1 }

-- 1.3.6.1.4.1.11.2.3.9.4.2.1.1.2.7   
auto-continue   OBJECT-TYPE
   SYNTAX          INTEGER {
                       eOff(1),
                      eOn(2)
               }   
   ACCESS           read-write    
   STATUS            optional   
   DESCRIPTION "Indicates if the device will automatically continue after
   encountering a continuable error. If AUTO-CONTINUE is set to
   eOn, the device will automatically generate continue event to
   acknowledge continuable errors. If AUTO-CONTINUE is set to
   eOff, then some other continue event will have to acknowledge
   the continuable error.Interaction May not be settable if NOT-IDLE contains the cProcessingPDL
   item. See continue object for a   description  of continuable errors"
::= { status-system 7 }

-- 1.3.6.1.4.1.11.2.3.9.4.2.1.1.25.17   
protect-ews-info-tab   OBJECT-TYPE
   SYNTAX          INTEGER {
                       eOff(1),
                      eOn(2)
               }   
   ACCESS           read-write    
   STATUS            optional   
   DESCRIPTION " This PML object is used by the WJA tool to allow administrators
   to enable or disable EWS information tab protection. When this
   option in selected/turned on the user will not be able to
   access anything on the EWS without logging in with the EWS
   device <<hidden>>(in case the EWS device <<hidden>> is configured).
   If the option is turned off the user will be able to access the
   information tab on the EWS page without providing the EWS
   device <<hidden>>(in case the EWS device <<hidden>> is configured),
   for all other tabs on the EWS page the user will have to login with EWS device <<hidden>>"
::= { settings-system2 17 }

-- 1.3.6.1.4.1.11.2.3.9.4.2.1.1.4.6.1.5   
ews-request-control-panel-supplies-status   OBJECT-TYPE
   SYNTAX          INTEGER {
                       eFalse(1),
                      eTrue(2)
               }   
   ACCESS           read-write    
   STATUS            optional   
   DESCRIPTION " System variable EWS_REQUEST_CONTROL_PANEL_SUPPPLIES_STATUS
   requires a PML interface so that WJA can directly access it
   without needing EWS support for that"
::= { settings-web-server 5 }

-- 1.3.6.1.4.1.11.2.3.9.4.2.1.6.2   
channelprinteralert   OBJECT-TYPE
   SYNTAX          OCTET STRING    
   ACCESS           read-only   
   STATUS            optional   
   DESCRIPTION "Identifies the values of prtAlertIndex, prtAlertSeverityLevel,
   prtAlertGroup, prtAlertGroupIndex, prtAlertLocation, and
   prtAlertCode for the latest critical evnet in the
   prtAlertTable. The OCTET STRING string is defined as following: \\
                     <table>                    
                    -----------------------------------------------------
                    Field  | Filed  |   DESCRIPTION                      
                    Offset | Length | 
                    -----------------------------------------------------  
                      0    |    4   | the value of prtAlertIndex
                      4    |    4   | the value of prtAlertSeverityLevel
                      8    |    4   | the value of prtAlertGroup
                     12    |    4   | the value of prtAlertGroupIndex
                     16    |    4   | the value of prtAlertLocation
                     20    |    4   | the value of prtAlertCode
                    ------------------------------------------------------
                    </table> \\ 
	   Each field is in Big Endian style"
::= { channel 2 }

-- 1.3.6.1.4.1.11.2.3.9.4.2.1.1.3.1   
model-number   OBJECT-TYPE
   SYNTAX          OCTET STRING    
   ACCESS           read-only    
   STATUS            optional   
   DESCRIPTION " Identifies the device model number as listed in the HP
   corporate price list (e.g. C2121A for DeskJet 500C). The string
   is as specific as possible. Products should note in POS if the
   model number on the CPL changes but the device reports the
   previous model number. If the model number changes based on the
   installed options, the POS should indicate if only the base
   model number is returned, or if the device senses the installed
   options and returns the correct model number. If possible,
   encode the model number in a symbol set (like Roman-8) that
   matches the ASCII character set and limit the characters used
   to ASCII characters"
::= { id 1 }

-- 1.3.6.1.4.1.11.2.3.9.4.2.1.1.2.19   
service-id   OBJECT-TYPE
   SYNTAX          OCTET STRING    
   ACCESS           read-write    
   STATUS            optional   
   DESCRIPTION " A read of this object will return the current SERVICE ID value
   in the printer. The format is 'YYDDD' where: \\ 
       YY = calendar year - 1990 \\ 
       DDD = (calendar month - 1) * 30 + (calendar day of the
       month or 30, if > 30) \\ 
	A write of this object will only succeed if the
	MANUFACTURING-CONTROL PML object has been set with the correct
	<<hidden>>. If the write operation is not allowed, this object
	will return an <ErrorActionCanNotBePerformedNow> status"
::= { status-system 19 }

-- 1.3.6.1.4.1.11.2.3.9.4.2.1.1.2.8   
install-date    OBJECT-TYPE
   SYNTAX          OCTET STRING    
   ACCESS           read-write    
   STATUS            optional   
   DESCRIPTION " Identifies the date that the device was installed. The format
   of the string is 'YYYYMMDDHHmmZ'. Where: \\ 
       YYYY is the year. \\ 
       MM is the month (1-12). \\ 
       DD is the day (1-31). \\ 
       HH is the hour of the day (0-23). \\ 
       mm are the minutes (0-59). \\ 
       'Z' designates Greenwich Mean Time; if 'Z' not specified,
   	value is local time. \\ 
	Device POS must specify the conditions for setting this	object"
::= { status-system 8 }

-- 1.3.6.1.4.1.11.2.3.9.4.2.1.1.3.3   
serial-number   OBJECT-TYPE
   SYNTAX          OCTET STRING    
   ACCESS           read-write    
   STATUS            optional   
   DESCRIPTION " Identifies the serial number for the device. If the
   SERIAL-NUMBER object is set by the user, then setting the
   object does not need to be protected. If the SERIAL-NUMBER
   object is set at the factory, then the <<hidden>> object
   must be set correctly before the SERIAL-NUMBER object is
   writable. If this is a writable object, the POS should indicate
   the maximum supported string length. If possible, encode the
   serial number in a symbol set (like Roman-8) that matches the
   ASCII character set and limit the characters used to ASCII
   characters"
::= { id 3 }

-- 1.3.6.1.4.1.11.2.3.9.4.2.1.1.3.2   
model-name   OBJECT-TYPE
   SYNTAX          OCTET STRING    
   ACCESS           read-only    
   STATUS            optional   
   DESCRIPTION " Identifies the device model name (e.g. ''DeskJet 1200C''). The
   string is as specific as possible. Capitalization and spacing
   should match family naming conventions. Products should note in
   POS if the model name on the HP corporate price list changes
   but the device reports the previous device name. If the model
   name changes based on the installed options, the POS should
   indicate if only the base model name is returned, or if the
   device senses the installed options and returns the correct
   model name. If possible, encode the model name in a symbol set
   (like Roman-8) that matches the ASCII character set and limit
   the characters used to ASCII characters"
::= { id 2 }

-- 1.3.6.1.4.1.11.2.3.9.4.2.1.1.3.16.0
model-derivative   OBJECT-TYPE
   SYNTAX          INTEGER    
   ACCESS           read-only    
   STATUS            optional   
   DESCRIPTION      "Identifies the device model derivative to distinguish among
   devices with identical MODEL-NAME and identical or unknown
   MODEL-NUMBER values. The device POS must specify the values
   returned by this object and their meanings."
::= { id 16 }

-- 1.3.6.1.4.1.11.2.3.9.4.2.1.1.3.10   
device-name   OBJECT-TYPE
   SYNTAX          OCTET STRING    
   ACCESS           read-write    
   STATUS            optional   
   DESCRIPTION " User defined device name. The POS should indicate the maximum
   supported string length. If the user entered string is too
   long, the device will store as much as possible and will return
   the <OKNearestLegal ValueSubstituted>"
::= { id 10 }

-- 1.3.6.1.4.1.11.2.3.9.4.2.1.1.3.11   
device-location   OBJECT-TYPE
   SYNTAX          OCTET STRING    
   ACCESS           read-write    
   STATUS            optional   
   DESCRIPTION " User defined device location. The POS should indicate the
   maximum supported string length. If the user entered string is
   too long, the device will store as much as possible and will
   return the <OKNearestLegal ValueSubstituted>"
::= { id 11 }

-- 1.3.6.1.4.1.11.2.3.9.4.2.1.1.3.12   
asset-number   OBJECT-TYPE
   SYNTAX          OCTET STRING    
   ACCESS           read-write    
   STATUS            optional   
   DESCRIPTION " User defined asset number. The POS should indicate the maximum
   supported string length. If the user entered string is too
   long, the device will store as much as possible and will return
   the <OKNearestLegal ValueSubstituted>"
::= { id 12 }

-- 1.3.6.1.4.1.11.2.3.9.4.2.1.1.6.5.28.14. 
job-info-accounting-job-type   OBJECT-TYPE
   SYNTAX          INTEGER {
                       ePrintJob(1),
                      eIPPJob(2),
                      eCopyJob(3),
                      eCopyInterruptJob(4),
                      eJetSendJob(5),
                      eInternalPage(6),
                      eCleaningPage(7),
                      eAutoCleaningPage(8),
                      eDigitalSendJob(9),
                      eWebPrintJob(10),
                      eFaxPrintJob(11),
                      eRetrievedJob(12),
                      ePhotoCardPrintJob(13),
                      eUnknownJob(1000)
               }   
   ACCESS           read-only    
   STATUS            optional   
   DESCRIPTION " Keeps track of what type of job is processed."
::= { job-info-accounting 14 }

-- 1.3.6.1.4.1.11.2.3.9.4.2.1.1.6.5.13. 
job-info-pages-printed   OBJECT-TYPE
   SYNTAX          INTEGER    
   ACCESS           read-only   
   STATUS            optional   
   DESCRIPTION " Indicates the number of pages printed by the destination
   subsystem. If none of the cSourceSubsystem,
   cProcessingSubsystem or cDestinationSubsystem items are in the
   associated JOB-INFO-STAGE object, then this object contains the
   total number of pages printed for this job. This value may
   increase by two each time for duplex jobs. The last OID field
   for this dynamic object contains the job ID"
::= { job-info 13 }

-- 1.3.6.1.4.1.11.2.3.9.4.2.1.1.6.5.14. 
job-info-size   OBJECT-TYPE
   SYNTAX          INTEGER    
   ACCESS           read-only    
   STATUS            optional   
   DESCRIPTION " Indicates the number of bytes of data processed by the
   processing subsystem. If neither of the cSourceSubsystem or
   cProcessingSubsystem items are in the associated JOB-INFO-STAGE
   object, then this object contains the size of this job, in
   bytes. The last OID field for this dynamic object contains the job ID"
::= { job-info 14 }

-- 1.3.6.1.4.1.11.2.3.9.4.2.1.1.6.5.22. 
job-info-physical-outbins-used   OBJECT-TYPE
   SYNTAX          INTEGER {
                       cOutbin1(0),
                      cOutbin2(1),
                      cOutbin3(2),
                      cOutbin4(3),
                      cOutbin5(4),
                      cOutbin6(5),
                      cOutbin7(6),
                      cOutbin8(7),
                      cOutbin9(8),
                      cOutbin10(9),
                      cOutbin11(10),
                      cOutbin12(11),
                      cOutbin13(12),
                      cOutbin14(13),
                      cOutbin15(14),
                      cOutbin16(15),
                      cOutbin17(16)
               }   
   ACCESS           read-only    
   STATUS            optional   
   DESCRIPTION " Indicates which physical output bins this job has delivered
   printed pages to. The last OID field for this dynamic object
   contains the job ID"
::= { job-info 22 }

-- 1.3.6.1.4.1.11.2.3.9.4.2.1.1.6.5.20. 
job-info-outbins-used   OBJECT-TYPE
   SYNTAX          INTEGER {
                       cOutbin1(0),
                      cOutbin2(1),
                      cOutbin3(2),
                      cOutbin4(3),
                      cOutbin5(4),
                      cOutbin6(5),
                      cOutbin7(6),
                      cOutbin8(7),
                      cOutbin9(8),
                      cOutbin10(9),
                      cOutbin11(10),
                      cOutbin12(11),
                      cOutbin13(12),
                      cOutbin14(13),
                      cOutbin15(14),
                      cOutbin16(15),
                      cOutbin17(16)
               }   
   ACCESS           read-only    
   STATUS            optional   
   DESCRIPTION " Indicates which output bins this job has delivered printed
   pages to. The last OID field for this dynamic object contains
   the job ID"
::= { job-info 20 }

-- 1.3.6.1.4.1.11.2.3.9.4.2.1.1.6.5.28.1. 
job-info-accounting-media-size   OBJECT-TYPE
   SYNTAX          INTEGER {
                       eUSExecutive(1),
                      eUSLetter(2),
                      eUSLegal(3),
                      eFoolscap(10),
                      eLedger(11),
                      eROC16K(17),
                      eJISExecutive(18),
                      eROC8K(19),
                      eISOandJISA6(24),
                      eISOandJISA5(25),
                      eISOandJISA4(26),
                      eISOandJISA3(27),
                      ePRC8K270X390(33),
                      ePRC16K195X270(34), 
                      ePRC8K260X368(35),
                      eJISB6(44),
                      eJISB5(45),
                      eJISB4(46),
                      eISOB5(65),
                      eJapansePostcardSingle(71),
                      eJapansePostcardDouble(72),
                      eISOA6Postcard(73),
                      eIndexCard4x6(74),
                      eIndexCard5x8(75),
                      ePhoto4x6(76),                      
                      eJapanesePostcardWithTab(77),           
                      eMonarch(80),
                      eCommercial10(81),
                      ePRC16K184X260(89),
                      eInternationalDL(90),
                      eInternationalC5(91),
                      eInternationalC6(92),
                      eInternationalB5(100),
                      eCustom(101),
                      eUSEnvelopeA2(109),
                      eJapanseEnvLong3(110),
                      eJapanseEnvLong4(111),
                      eUSExecutiveR(257),
                      eUSLetterR(258),
                      eROC16KR(273),
                      eISOandJISA6R(280),
                      eISOandJISA5R(281),
                      eISOandJISA4R(282),
                      eJISBR6R(300),
                      eJISB5R(301),
                      eAnyCustomSize(32764),
                      eAnySize(32765),
                      eCustomRoll(32766),
                      eUnknownMediaSize(32767)
               }   
   ACCESS           read-only    
   STATUS            optional   
   DESCRIPTION " Contains the media size of the printed job. The media size of
   the first page will decide the media size of the entire job.
   The return value of this object will only be valid when the
   printer finishes printing the entire job"
::= { job-info-accounting 1 }

-- 1.3.6.1.4.1.11.2.3.9.4.2.1.1.6.5.28.2. 
job-info-accounting-media-type   OBJECT-TYPE
   SYNTAX          INTEGER {
                       eUnknownMedia(1),
                      eStandardType(2),
                      ePreprinted(3),
                      eLetterhead(4),
                      eTransparency(5),
                      ePrepunched(6),
                      eLabels(7),
                      eBond(8),
                      eRecycled(9),
                      eColored(10),
                      eCardStock(11),
                      eRough(12),
                      eVellum(13),
                      eHeavy(14),
                      eGloss(15),
                      eUserType1(16),
                      eUserType2(17),
                      eUserType3(18),
                      eUserType4(19),
                      eUserType5(20),
                      ePhotoGlossy(24),
                      ePhotoQualityGlossy(25),
                      ePhotoQualityMatte(26),
                      eEverydayPhotoGlossy(27),
                      eEverydayPhotoMatte(28),
                      ePremiumInkjet(29),      
                      ePremiumInkjetHeavy(30),
                      eBrochureGlossy(31),
                      eBrochureMatte(32),
                      ePremiumPhotoGlossy(33),
                      ePremiumPlussPhotoGlossy(34),
                      ePremiumPlusPhotoMatte(35),
                      eColorfastPhotoGlossy(36),
                      ePremiumTransparency(37),
                      ePremiumPlusTranparency(38),
                      eNHPHeavyGloss(39),
                      eExtraHeavy(40),
                      eHighGlossImages(41),
                      eIntermediate(42),
                      eTab(43),
                      eExtraHeavyGloss(44),
                      eHPIJTrans(45),
                      eHPSnowman160(46),
                      eHPSnowman220(47),
                      eHPPremMatte(48),
                      eHPBrochMatte(49),
                      eHPCoverMatte(50),
                      eHPMatte(51),
                      eCoverMatte(52),
                      eHPOfficePaper(53),                      
                      eHPOfficePaperEU(54),                      
                      eLastMedia(55)
               }   
   ACCESS           read-only    
   STATUS            optional   
   DESCRIPTION " Contains the media type of the printed job. The media type of
   the first page will decide the media type of the entire job.
   The return value of this object will only be valid when the
   printer finishes printing the entire job"
::= { job-info-accounting 2 }

-- 1.3.6.1.4.1.11.2.3.9.4.2.1.1.6.5.28.4. 
job-info-accounting-media-simplex-count   OBJECT-TYPE
   SYNTAX          INTEGER    
   ACCESS           read-only    
   STATUS            optional   
   DESCRIPTION " Contains the total number of simplex pages printed in a
   particular job"
::= { job-info-accounting 4 }

-- 1.3.6.1.4.1.11.2.3.9.4.2.1.1.6.5.28.5. 
job-info-accounting-media-duplex-count   OBJECT-TYPE
   SYNTAX          INTEGER    
   ACCESS           read-only    
   STATUS            optional   
   DESCRIPTION " Contains the total number of duplex pages printed in a
   particular job"
::= { job-info-accounting 5 }

-- 1.3.6.1.4.1.11.2.3.9.4.2.1.1.6.5.28.6. 
job-info-accounting-grayscale-impression-count   OBJECT-TYPE
   SYNTAX          INTEGER    
   ACCESS           read-only    
   STATUS            optional   
   DESCRIPTION " Contains the total number of monochrome pages printed in a
   particular job"
::= { job-info-accounting 6 }

-- 1.3.6.1.4.1.11.2.3.9.4.2.1.1.6.5.28.7. 
job-info-accounting-color-impression-count   OBJECT-TYPE
   SYNTAX          INTEGER    
   ACCESS           read-only    
   STATUS            optional   
   DESCRIPTION " Contains the total number of color pages printed in a
   particular job"
::= { job-info-accounting 7 }

-- 1.3.6.1.4.1.11.2.3.9.4.2.1.1.6.5.28.8. 
job-info-accounting-black-dots   OBJECT-TYPE
   SYNTAX          INTEGER    
   ACCESS           read-only    
   STATUS            optional   
   DESCRIPTION " Contains the total number of black pixels used in a particular
   job"
::= { job-info-accounting 8 }

-- 1.3.6.1.4.1.11.2.3.9.4.2.1.1.6.5.28.9. 
job-info-accounting-yellow-dots   OBJECT-TYPE
   SYNTAX          INTEGER    
   ACCESS           read-only    
   STATUS            optional   
   DESCRIPTION " Contains the total number of yellow pixels used in a particular
   job"
::= { job-info-accounting 9 }

-- 1.3.6.1.4.1.11.2.3.9.4.2.1.1.6.5.28.10. 
job-info-accounting-cyan-dots   OBJECT-TYPE
   SYNTAX          INTEGER    
   ACCESS           read-only    
   STATUS            optional   
   DESCRIPTION " Contains the total number of cyan pixels used in a particular
   job"
::= { job-info-accounting 10 }

-- 1.3.6.1.4.1.11.2.3.9.4.2.1.1.6.5.28.11. 
job-info-accounting-magenta-dots   OBJECT-TYPE
   SYNTAX          INTEGER    
   ACCESS           read-only    
   STATUS            optional   
   DESCRIPTION " Contains the total number of magenta pixels used in a
   particular job"
::= { job-info-accounting 11 }

-- 1.3.6.1.4.1.11.2.3.9.4.2.1.1.6.5.28.33. 
job-info-accounting-fixer-dots   OBJECT-TYPE
   SYNTAX          INTEGER    
   ACCESS           read-only    
   STATUS            optional   
   DESCRIPTION " Contains the total number of fixer pixels used in a particular
   job"
::= { job-info-accounting 33 }

-- 1.3.6.1.4.1.11.2.3.9.4.2.1.1.6.5.28.3. 
job-info-accounting-finishing-options   OBJECT-TYPE
   SYNTAX          INTEGER {
                       eNoFinish(1),
                      eOffset(2),
                      ePunch(3),
                      eStapler(4),
                      eFinisher(5),
                      eBinding(6),
                      eCustom1(11),
                      eCustom2(12),
                      eCustom3(13),
                      eCustom4(14),
                      eCustom5(15),
                      eOther(20)
               }   
   ACCESS           read-only    
   STATUS            optional   
   DESCRIPTION " Contains the finishing option used on the printed job. The
   finishing option specified for the first page will decide the
   finishing option of the entire job. The return value of this
   object will only be valid when the printer finishes printing
   the entire job"
::= { job-info-accounting 3 }

-- 1.3.6.1.4.1.11.2.3.9.4.2.1.1.6.5.11. 
job-info-io-source   OBJECT-TYPE
   SYNTAX          INTEGER    
   ACCESS           read-only    
   STATUS            optional   
   DESCRIPTION " Indicates which I/O source, the print job was received over.
   The value maps to port numbering scheme supported in the
   DEVICE/SOURCE-SUBSYSTEM/IO/PORTS sub-tree"
::= { job-info 11 }

-- 1.3.6.1.4.1.11.2.3.9.4.2.1.1.6.5.1. 
job-info-name1   OBJECT-TYPE
   SYNTAX          OCTET STRING    
   ACCESS           read-only    
   STATUS            optional   
   DESCRIPTION " Contains the first part of this print job's name. The last OID
   field for this dynamic object contains the job ID"
::= { job-info 1 }

-- 1.3.6.1.4.1.11.2.3.9.4.2.1.1.6.5.2. 
job-info-name2   OBJECT-TYPE
   SYNTAX          OCTET STRING    
   ACCESS           read-only    
   STATUS            optional   
   DESCRIPTION " Contains the second part of this print job's name. The last OID
   field for this dynamic object contains the job ID"
::= { job-info 2 }

-- 1.3.6.1.4.1.11.2.3.9.4.2.1.1.6.5.23.1. 
job-info-attr-1   OBJECT-TYPE
   SYNTAX          OCTET STRING    
   ACCESS           read-only    
   STATUS            optional   
   DESCRIPTION " Returns the value that was set in PJL via the SET JOBATTR=
   command. Attribute objects are saved sequentially, starting
   with 1, after the start of a job. If more attributes are set
   than there are objects to store them, the excess JOBATTR values
   are ignored. If the corresponding SET JOBATTR= command has not
   been received when a get is done for this object, a status of
   <ErrorUnknownObjectIdentifier> will be returned"
::= { job-info-attribute 1 }

-- 1.3.6.1.4.1.11.2.3.9.4.2.1.1.6.5.23.2. 
job-info-attr-2   OBJECT-TYPE
   SYNTAX          OCTET STRING    
   ACCESS           read-only    
   STATUS            optional   
   DESCRIPTION " Returns the value that was set in PJL via the SET JOBATTR=
   command. See JOB-INFO-ATTR-1 for details"
::= { job-info-attribute 2 }

-- 1.3.6.1.4.1.11.2.3.9.4.2.1.1.6.5.23.3. 
job-info-attr-3   OBJECT-TYPE
   SYNTAX          OCTET STRING    
   ACCESS           read-only    
   STATUS            optional   
   DESCRIPTION " Returns the value that was set in PJL via the SET JOBATTR=
   command. See JOB-INFO-ATTR-1 for details"
::= { job-info-attribute 3 }

-- 1.3.6.1.4.1.11.2.3.9.4.2.1.1.6.5.23.4. 
job-info-attr-4   OBJECT-TYPE
   SYNTAX          OCTET STRING    
   ACCESS           read-only    
   STATUS            optional   
   DESCRIPTION " Returns the value that was set in PJL via the SET JOBATTR=
   command. See JOB-INFO-ATTR-1 for details"
::= { job-info-attribute 4 }

-- 1.3.6.1.4.1.11.2.3.9.4.2.1.1.6.5.23.5. 
job-info-attr-5   OBJECT-TYPE
   SYNTAX          OCTET STRING    
   ACCESS           read-only    
   STATUS            optional   
   DESCRIPTION " Returns the value that was set in PJL via the SET JOBATTR=
   command. See JOB-INFO-ATTR-1 for details"
::= { job-info-attribute 5 }

-- 1.3.6.1.4.1.11.2.3.9.4.2.1.1.6.5.23.6. 
job-info-attr-6   OBJECT-TYPE
   SYNTAX          OCTET STRING    
   ACCESS           read-only    
   STATUS            optional   
   DESCRIPTION " Returns the value that was set in PJL via the SET JOBATTR=
   command. See JOB-INFO-ATTR-1 for details"
::= { job-info-attribute 6 }

-- 1.3.6.1.4.1.11.2.3.9.4.2.1.1.6.5.23.7. 
job-info-attr-7   OBJECT-TYPE
   SYNTAX          OCTET STRING    
   ACCESS           read-only    
   STATUS            optional   
   DESCRIPTION " Returns the value that was set in PJL via the SET JOBATTR=
   command. See JOB-INFO-ATTR-1 for details"
::= { job-info-attribute 7 }

-- 1.3.6.1.4.1.11.2.3.9.4.2.1.1.6.5.23.8. 
job-info-attr-8   OBJECT-TYPE
   SYNTAX          OCTET STRING    
   ACCESS           read-only    
   STATUS            optional   
   DESCRIPTION " Returns the value that was set in PJL via the SET JOBATTR=
   command. See JOB-INFO-ATTR-1 for details"
::= { job-info-attribute 8 }

-- 1.3.6.1.4.1.11.2.3.9.4.2.1.1.6.5.23.9. 
job-info-attr-9   OBJECT-TYPE
   SYNTAX          OCTET STRING    
   ACCESS           read-only    
   STATUS            optional   
   DESCRIPTION " Returns the value that was set in PJL via the SET JOBATTR=
   command. See JOB-INFO-ATTR-1 for details"
::= { job-info-attribute 9 }

-- 1.3.6.1.4.1.11.2.3.9.4.2.1.1.6.5.23.10. 
job-info-attr-10   OBJECT-TYPE
   SYNTAX          OCTET STRING    
   ACCESS           read-only    
   STATUS            optional   
   DESCRIPTION " Returns the value that was set in PJL via the SET JOBATTR=
   command. See JOB-INFO-ATTR-1 for details"
::= { job-info-attribute 10 }

-- 1.3.6.1.4.1.11.2.3.9.4.2.1.1.6.5.23.11. 
job-info-attr-11   OBJECT-TYPE
   SYNTAX          OCTET STRING    
   ACCESS           read-only    
   STATUS            optional   
   DESCRIPTION " Returns the value that was set in PJL via the SET JOBATTR=
   command. See JOB-INFO-ATTR-1 for details"
::= { job-info-attribute 11 }

-- 1.3.6.1.4.1.11.2.3.9.4.2.1.1.6.5.23.12. 
job-info-attr-12   OBJECT-TYPE
   SYNTAX          OCTET STRING    
   ACCESS           read-only    
   STATUS            optional   
   DESCRIPTION " Returns the value that was set in PJL via the SET JOBATTR=
   command. See JOB-INFO-ATTR-1 for details"
::= { job-info-attribute 12 }

-- 1.3.6.1.4.1.11.2.3.9.4.2.1.1.6.5.23.13. 
job-info-attr-13   OBJECT-TYPE
   SYNTAX          OCTET STRING    
   ACCESS           read-only    
   STATUS            optional   
   DESCRIPTION " Returns the value that was set in PJL via the SET JOBATTR=
   command. See JOB-INFO-ATTR-1 for details"
::= { job-info-attribute 13 }

-- 1.3.6.1.4.1.11.2.3.9.4.2.1.1.6.5.23.14. 
job-info-attr-14   OBJECT-TYPE
   SYNTAX          OCTET STRING    
   ACCESS           read-only    
   STATUS            optional   
   DESCRIPTION " Returns the value that was set in PJL via the SET JOBATTR=
   command. See JOB-INFO-ATTR-1 for details"
::= { job-info-attribute 14 }

-- 1.3.6.1.4.1.11.2.3.9.4.2.1.1.6.5.23.15. 
job-info-attr-15   OBJECT-TYPE
   SYNTAX          OCTET STRING    
   ACCESS           read-only    
   STATUS            optional   
   DESCRIPTION " Returns the value that was set in PJL via the SET JOBATTR=
   command. See JOB-INFO-ATTR-1 for details"
::= { job-info-attribute 15 }

-- 1.3.6.1.4.1.11.2.3.9.4.2.1.1.6.5.23.16. 
job-info-attr-16   OBJECT-TYPE
   SYNTAX          OCTET STRING    
   ACCESS           read-only    
   STATUS            optional   
   DESCRIPTION " Returns the value that was set in PJL via the SET JOBATTR=
   command. See JOB-INFO-ATTR-1 for details"
::= { job-info-attribute 16 }

-- 1.3.6.1.4.1.11.2.3.9.4.2.1.1.6.5.15. 
job-info-state   OBJECT-TYPE
   SYNTAX          INTEGER {
                       eAborted(3),
                      eWaitingForResources(4),
                      ePrinted(5),
                      eRetained(6),
                      eTerminating(7),
                      eInterrupted(8),
                      ePaused(9),
                      eCancelled(10),
                      eProcessing(11),
                      eScanning(12),
                      eSending(13),
                      eStored(14)
               }   
   ACCESS           read-only   
   STATUS            optional   
   DESCRIPTION " Indicates the state of the job. The last OID field for this
   dynamic object contains the job ID. \\ 
       eAborted - the print job was aborted. \\ 
       eWaitingForResources - the print job requires resources
       that are not currently available. Example resources
       that can cause the job to wait include the print engine
       or PDL processor being unavailable. The print engine
	could be unavailable due to paper out, paper jam,
	staple out, stapler jam, marking agent low, output bin
        full, etc. The PDL processor could be unavailable due
	to an off-line condition. Each printer specific object
	specification should state which conditions cause a job
        to be waiting for resources and also state which
	objects can be retrieved by an application to determine
	the exact cause of a resource being unavailable. \\ 
	ePrinted - the job has printed. The related JOB-INFO-
	OUTCOME object indicates if any problems were
	encountered while the job was processed. \\ 
        eRetained - the job can be reprinted. \\ 
    eTerminating - the job was aborted or cancelled and is
	currently is terminating. \\ 
        eInterrupted - the job has been interrupted. The job can be
	continued. \\ 
	ePaused - the job has been paused. The job can be
	continuted. \\ 
	eCancelled - the job has been cancelled. \\ 
	eProcessing - the job is currently being printed normally.
	eStored - The job is stored on the device and can be retrieved
	and printed at a later point in time"
::= { job-info 15 }

-- 1.3.6.1.4.1.11.2.3.9.4.2.1.1.6.5.19. 
job-info-outcome   OBJECT-TYPE
   SYNTAX          INTEGER {
                       eOk(3),
                      eWarningsEncountered(4),
                      eErrorsEncountered(5)
               }   
   ACCESS           read-only    
   STATUS            optional   
   DESCRIPTION " Indicates if any warning or error conditions were encountered
   while processing the assoicated job. The last OID field for
   this dynamic object contains the job ID"
::= { job-info 19 }

-- 1.3.6.1.4.1.11.2.3.9.4.2.1.1.6.5.12. 
job-info-pages-processed   OBJECT-TYPE
   SYNTAX          INTEGER    
   ACCESS           read-only    
   STATUS            optional   
   DESCRIPTION " Indicates the number of pages processed by the processing
   subsystem. If neither the cSourceSubsystem or the
   cProcessingSubsystem items are in the associated JOB-INFO-STAGE
   object, then this object contains the total number of pages
   processed for this job. The last OID field for this dynamic
   object contains the job ID"
::= { job-info 12 }

-- 1.3.6.1.4.1.11.2.3.9.4.2.1.3.3.1.13   
default-media-size   OBJECT-TYPE
   SYNTAX          INTEGER {
                       eUSExecutive(1),
                      eUSLetter(2),
                      eUSLegal(3),
                      eUSEDP(4),
                      eEuropeanEDP(5),
                      eReservedDoNotUse(6),
                      eUSGovernmentLetter(7),
                      eUSGovernmentLegal(8),
                      eFolio(9),
                      eFoolscap(10),
                      eLedger(11),
                      eCSize(12),
                      eDSize(13),
                      eESize(14),
                      eStatement(15),
                      eSuperB(16),
                      eROC16K(17),
                      eJISExecutive(18),
                      eROC8K(19),
                      eISOandJISA10(20),
                      eISOandJISA9(21),
                      eISOandJISA8(22),
                      eISOandJISA7(23),
                      eISOandJISA6(24),
                      eISOandJISA5(25),
                      eISOandJISA4(26),
                      eISOandJISA3(27),
                      eISOandJISA2(28),
                      eISOandJISA1(29),
                      eISOandJISA0(30),
                      eISOandJIS2A0(31),
                      eISOandJIS4A0(32),
                      ePRC8K270X390(33),
                      ePRC16K195X270(34),
                      ePRC8K260X368(35),
                      eISORA4(36),
                      eISOSRA4(37),
                      eISORA3(39),
                      eJISB10(40),
                      eJISB9(41),
                      eJISB8(42),
                      eJISB7(43),
                      eJISB6(44),
                      eJISB5(45),
                      eJISB4(46),
                      eJISB3(47),
                      eJISB2(48),
                      eJISB1(49),
                      eJISB0(50),
                      eISOB10(60),
                      eISOB9(61),
                      eISOB8(62),
                      eISOB7(63),
                      eISOB6(64),
                      eISOB5(65),
                      eISOB4(66),                      
                      eISOB3(67),
                      eISOB2(68),
                      eISOB1(69),
                      eISOB0(70),
                      eJapansePostcardSingle(71),
                      eJapansePostcardDouble(72),
                      eISOA6Postcard(73),
                      eIndexCard4x6(74),
                      eIndexCard5x8(75),
                      ePhoto4x6(76),
                      eJapanesePostcardWithTab(77),
                      eIndexCard3x5(78),
                      eCommercial9(79),
                      eMonarch(80),
                      eCommercial10(81),
                      eCatalog(82),
                      eNo10Envelope(83),
                      ePRC16K184X260(89),
                      eInternationalDL(90),
                      eInternationalC5(91),
                      eInternationalC6(92),
                      eInternationalC4(93),
                      eInternationalB5(100),
                      eCustom(101),
                      eCustomCard(108),                      
                      eUSEnvelopeA2(109),
                      eJapanseEnvLong3(110),
                      eJapanseEnvLong4(111),
                      eJapaneseEnv2(112),
                      ePhoto10x15(118),
                      ePhotoCabinet(119),
                      eTabloidExtra(120),
                      ePhotoLSizeCard(121),
                      eIndexCard5x7(122),
                      ePhotoESizeCard(123),
                      ePhotoKGSizeCard(124),
                      ePhoto2ESizeCard(125),
                      ePhoto2LSizeCard(126),
                      eUSExecutiveR(257),
                      eUSLetterR(258),
                      eROC16KR(273),
                      eISOandJISA6R(280),
                      eISOandJISA5R(281),
                      eISOandJISA4R(282),
                      eJISBR6R(300),
                      eJISB5R(301),
                      eStatementR(302),
                      eAnyCustomSize(32764),
                      eAnySize(32765),
                      eCustomRoll(32766),                      
                      eUnknownMediaSize(32767),                      
                      eStatementWR(65234),
                      eJISB5WR(65235),
                      eISOandJISA4WR(65254),
                      eISOandJISA5WR(65255),
                      eUSLetterWR(65278),
                      eJISB4W(65490),
                      eJISB5W(65491),
                      eISOandJISA3W(65509),
                      eISOandJISA4W(65510),
                      eISOandJISA5W(65511),
                      eStatementW(65521),
                      eLedgerW(65530),
                      eUSLetterW(65534)
               }   
   ACCESS           read-write    
   STATUS            optional   
   DESCRIPTION " This indicates the default media size. A write of an
   unsupported value causes an <ErrorInvalidOrUnsupported Value>.
   Complete list of supported media sizes along with their
   dimensions are listed in the ''Media Size Table'' near the end
   of this document. (for a full list of media size enums see the
   end of this file)"
::= { settings-pdl 13 }

-- 1.3.6.1.4.1.11.2.3.9.4.2.1.3.3.1.22   
default-media-name   OBJECT-TYPE
   SYNTAX          OCTET STRING    
   ACCESS           read-write    
   STATUS            optional   
   DESCRIPTION " Returns or sets the media name that is used until the media
   name is changed by a print job command"
::= { settings-pdl 22 }

-- 1.3.6.1.4.1.11.2.3.9.4.2.1.4.1.15.1. 
media-size-supported-driver-n-string   OBJECT-TYPE
   SYNTAX          OCTET STRING    
   ACCESS           read-only    
   STATUS            mandatory   
   DESCRIPTION " Returns the Driver (PJL) string used to specigy a media size,
   for each media size that is supported by a product. PML walk of
   1.4.1.15.1 will return the driver (PJL) name string for each
   media size supported by a product. PML Get of 1.4.1.15.1.X will
   return the driver (PJL) name string of the media size whose PML
   ID maps to X (if it is supported)"
::= { media-sizes 1 }

-- 1.3.6.1.4.1.11.2.3.9.4.2.1.3.3.1.19   
cold-reset-media-size   OBJECT-TYPE
   SYNTAX          INTEGER {
                       eUSExecutive(1),
                      eUSLetter(2),
                      eUSLegal(3),
                      eUSEDP(4),
                      eEuropeanEDP(5),
                      eReservedDoNotUse(6),
                      eUSGovernmentLetter(7),
                      eUSGovernmentLegal(8),
                      eFolio(9),
                      eFoolscap(10),
                      eLedger(11),
                      eCSize(12),
                      eDSize(13),
                      eESize(14),
                      eStatement(15),
                      eSuperB(16),
                      eROC16K(17),
                      eJISExecutive(18),
                      eROC8K(19),
                      eISOandJISA10(20),
                      eISOandJISA9(21),
                      eISOandJISA8(22),
                      eISOandJISA7(23),
                      eISOandJISA6(24),
                      eISOandJISA5(25),
                      eISOandJISA4(26),
                      eISOandJISA3(27),                     
                      eISOandJISA2(28),
                      eISOandJISA1(29),
                      eISOandJISA0(30),
                      eISOandJIS2A0(31),
                      eISOandJIS4A0(32),
                      ePRC8K270X390(33),
                      ePRC16K195X270(34),
                      ePRC8K260X368(35),
                      eJISB10(40),
                      eJISB9(41),
                      eJISB8(42),
                      eJISB7(43),
                      eJISB6(44),
                      eJISB5(45),
                      eJISB4(46),
                      eJISB3(47),
                      eJISB2(48),
                      eJISB1(49),
                      eJISB0(50),
                      eISOB10(60),
                      eISOB9(61),
                      eISOB8(62),
                      eISOB7(63),
                      eISOB6(64),
                      eISOB5(65),
                      eISOB4(66),
                      eISOB3(67),
                      eISOB2(68),
                      eISOB1(69),
                      eISOB0(70),
                      eJapansePostcardSingle(71),
                      eJapansePostcardDouble(72),
                      eISOA6Postcard(73),
                      eIndexCard4x6(74),
                      eIndexCard5x8(75),
                      ePhoto4x6(76),
                      eJapanesePostcardWithTab(77),
                      eIndexCard3x5(78),
                      eMonarch(80),
                      eCommercial10(81),
                      eCatalog(82),
                      eNo10Envelope(83),
                      ePRC16K184X260(89),
                      eInternationalDL(90),
                      eInternationalC5(91),
                      eInternationalC6(92),
                      eInternationalC4(93),
                      eInternationalB5(100),
                      eCustom(101),
                      eCustomCard(108),
                      eUSEnvelopeA2(109),
                      eJapanseEnvLong3(110),
                      eJapanseEnvLong4(111),                      
                      eJapaneseEnv2(112),                      
                      ePhoto10x15(118),
                      ePhotoCabinet(119),
                      ePhotoLSizeCard(121),
                      eIndexCard5x7(122),
                      ePhotoESizeCard(123),
                      ePhotoKGSizeCard(124),
                      ePhoto2ESizeCard(125),
                      ePhoto2LSizeCard(126),
                      eUSExecutiveR(257),
                      eUSLetterR(258),
                      eROC16KR(273),
                      eISOandJISA6R(280),
                      eISOandJISA5R(281),
                      eISOandJISA4R(282),
                      eJISBR6R(300),
                      eJISB5R(301),
                      eStatementR(302),
                      eAnyCustomSize(32764),
                      eAnySize(32765),
                      eCustomRoll(32766),
                      eUnknownMediaSize(32767),
                      eStatementWR(65234),
                      eJISB5WR(65235),
                      eISOandJISA4WR(65254),                      
                      eISOandJISA5WR(65255),
                      eUSLetterWR(65278),
                      eJISB4W(65490),
                      eJISB5W(65491),
                      eISOandJISA3W(65509),
                      eISOandJISA4W(65510),
                      eISOandJISA5W(65511),
                      eStatementW(65521),
                      eLedgerW(65530),
                      eUSLetterW(65534)
               }   
   ACCESS           read-write    
   STATUS            optional   
   DESCRIPTION " Returns or sets the media size that is used as the
   DEFAULT-MEDIA-SIZE when a cold reset occurs"
::= { settings-pdl 19 }

-- 1.3.6.1.4.1.11.2.3.9.4.2.1.4.1.8.8.1   
media-number-of-type-supported   OBJECT-TYPE
   SYNTAX          INTEGER    
   ACCESS           read-only    
   STATUS            optional   
   DESCRIPTION " Indicates the maximum number of supported media types"
::= { media-types 1 }

-- 1.3.6.1.4.1.11.2.3.9.4.2.1.4.1.8.1.1   
media-names-available   OBJECT-TYPE
   SYNTAX          INTEGER {
                       cMediaName1Available(0),
                      cMediaName2Available(1),
                      cMediaName3Available(2),
                      cMediaName4Available(3),
                      cMediaName5Available(4),
                      cMediaName6Available(5),
                      cMediaName7Available(6),
                      cMediaName8Available(7),
                      cMediaName9Available(8),
                      cMediaName10Available(9),
                      cMediaName11Available(10),
                      cMediaName12Available(11),
                      cMediaName13Available(12),
                      cMediaName14Available(13),
                      cMediaName15Available(14),
                      cMediaName16Available(15),
                      cMediaName17Available(16),
                      cMediaName18Available(17),
                      cMediaName19Available(18),
                      cMediaName20Available(19),
                      cMediaName21Available(20),   
                      cMediaName22Available(21),
                      cMediaName23Available(22),
                      cMediaName24Available(23),
                      cMediaName25Available(24),
                      cMediaName26Available(25),
                      cMediaName27Available(26),
                      cMediaName28Available(27),
                      cMediaName29Available(28),
                      cMediaName30Available(29),
                      cMediaName31Available(30),
                      cMediaName32Available(31)
               }   
   ACCESS           read-write    
   STATUS            optional   
   DESCRIPTION " The value of this object controls which of the MEDIAx-NAME
   objects are supported. If a bit is set to zero, then attempting
   to get or set the corresponding MEDIAx-NAME objects will return
   <ErrorUnknownObjectIdentifier>"
::= { settings-print-media 1 }

-- 1.3.6.1.4.1.11.2.3.9.4.2.1.4.1.8.1.3   
media-names-enabled   OBJECT-TYPE
   SYNTAX          OCTET STRING    
   ACCESS           read-write    
   STATUS            optional   
   DESCRIPTION " The value of this object controls whish of the MEDIAx-NAME
   objects are supported. Of a bit is set to zero then the attempt
   to get or set the corresponding MEDIAx-NAME objects will return
   <ErrorUnknownObjectIdentifier>"
::= { settings-print-media 3 }

-- 1.3.6.1.4.1.11.2.3.9.4.2.1.1.6.7.2.4   
held-job-enable   OBJECT-TYPE
   SYNTAX          INTEGER {
                       eDisabled(1),
                      eEnabled(2)
               }   
   ACCESS           read-write    
   STATUS            optional   
   DESCRIPTION " Enables or disables Job Retention (Job Hold). The valid values
   are eDisabled and eEnabled. (Specifying an invalid mode causes
   an <ErrorInvalidOrUnsupportedValue> error to be returned.) When
   eDisabled is specified all Job Retention (Hold, Proof, Store,
   PIN Printing) is disabled. When eEnabled is specified, the Job
   Retention characteristics of a given job are defined by the PJL
   variable SET HOLD"
::= { held-job-control 4 }

-- 1.3.6.1.4.1.11.2.3.9.4.2.1.1.1.65   
power-state   OBJECT-TYPE
   SYNTAX          INTEGER {
                       ePowerStateAwake(1),
                      ePowerStatePowerSave(2),
                      ePowerStateSleep(3),
                      ePowerStateOff(4),
                      ePowerStateTransitioningToAwake(5),
                      ePowerStateTransitioningToPowerSave(6),
                      ePowerStateTransitioningToSleep(7),
                      ePowerStateTransitioningToOff(8),
                      ePowerStateReboot(9),
                      ePowerStateAutoOff(10),
                      ePowerState1Watt(11)
               }   
   ACCESS           read-write    
   STATUS            optional   
   DESCRIPTION " This object is used to inquire about and to control the 'power
   state' of the device. The exact meaning of each enumeration may
   vary from device to device, but the general interpretation is
   as follows: ePowerStateAwake: The device is idle (immediately
   ready to process a job) or processing a job.
   ePowerStatePowerSave: The device is in a low power state and
   will not be immediately available to process an incoming job. A
   'warm-up time' of several seconds can be expected.
   ePowerStateSleep: The device is in a sleep state. It uses less
   power than when in the power save state. It can also be
   expected to need a substantially longer warm-up time than when
   in the power save state. ePowerStateOff: The device is powered
   off. Note that when the device is powered off then SNMP/PML
   requests obviously cannot be honored. Therefore ePowerStateOff
   will likely never be returned from a PML get operation.
   However, ePowerStateOff could potentially be used in a PML set
   operation to power down the device if it has a
   software/firmware controllable power switch. For a given
   product it may not be possible to have the device enter the
   requested state due to the current state of the device. E.g.,
   it may not be possible to enter the power save state if the
   device currently is in the sleep state. In this case a set
   operation will have an execution outcome of
   <ErrorActionCanNotBePerformedNow>. The same execution outcome
   can be expected if the device is processing a job and an
   attempt is made to e.g. bring the device into the power save
   state or the sleep state. A get operation on the object returns
   the current power state of the device. While the device is
   transitioning from one state to another one of the values
   ePowerStateTransitioningToAwake,
   ePowerStateTransitioningToPowerSave,
   ePowerStateTransitioningToSleep or
   ePowerStateTransitioningToOff will be returned from a PML get
   operation. An attempt to perform a PML set with any of these
   four values will yield <ErrorInvalidOrUnsupportedValue>"
::= { settings-system 65 }

-- 1.3.6.1.4.1.11.2.3.9.4.2.1.1.1.1   
energy-star   OBJECT-TYPE
   SYNTAX          INTEGER     
   ACCESS           read-write    
   STATUS            optional    
   DESCRIPTION " Returns or changes the Energy Star sleep value. If the value
   is greater than zero, then the device will go into energy
   saving sleep mode after the print engine has been idle for the
   number of seconds specified by this object. A value of zero
   means Energy Star is disabled and the device will not go to
   sleep based on print engine idle time. The value must be
   non-negative."
::= { settings-system 1 }

-- 1.3.6.1.4.1.11.2.3.9.4.2.1.1.1.2   
sleep-mode   OBJECT-TYPE
   SYNTAX          INTEGER {
                       eFalse(1),
                      eTrue(2)
               }   
   ACCESS           read-write    
   STATUS            optional   
   DESCRIPTION " Returns eTrue if the device is in energy saving sleep mode,
   otherwise returns eFalse. Setting SLEEP-MODE to eFalse causes
   the device to wake up, if it is in sleep mode. Setting
   SLEEP-MODE to eTrue causes the device to go into sleep mode"
::= { settings-system 2 }

-- 1.3.6.1.4.1.11.2.3.9.4.2.1.1.1.89   
powersave-enable-type   OBJECT-TYPE
   SYNTAX          INTEGER {
                       ePowerSaveOff(1),
                      ePowerSaveUseSleepDelay(2),
                      ePowerSaveUseSleepSchedule(3),
                      ePowerSaveMaximize(4),
                      ePowerSaveCustom(5)
               }   
   ACCESS           read-write    
   STATUS            optional   
   DESCRIPTION " ePowerSaveOff - printer stays awake all the time, can only
   sleep if sleep button is hit. ePowerSaveUseSleepDelay - use
   sleep delay the old way, sleep schedule is ignored .
   ePowerSaveUseSleepSchedule - sleep delay time is ignored, stay
   awake in wake period, sleep in 15 minutes in sleep period.
   ePowerSaveMaximize - set the sleep delay to 15 minutes, so
   wether in wake or sleep period it will sleep in 15 minutes.
   ePowerSaveCustom - set the sleep delay to 45 minutes, use sleep
   delay during wake period, sleep in 15 minutes in sleep period."
::= { settings-system 89 }

-- 1.3.6.1.4.1.11.2.3.9.4.2.1.1.25.19   
eprint-opt-in   OBJECT-TYPE
   SYNTAX          INTEGER {
                       eOff(1),
                      eOn(2)
               }   
   ACCESS           read-write    
   STATUS            optional   
   DESCRIPTION " This object is the master switch for the ePrint feature. By
   default this should be eOff(1). This differs from
   EPRINT-ENABLED in that ePrint connot be registered with the
   cloud when this is diabled while EPRINT-ENABLED allows
   registration and temporary disablement"
::= { settings-system2 19 }

-- 1.3.6.1.4.1.11.2.3.9.4.2.1.1.25.20   
eprint-enabled   OBJECT-TYPE
   SYNTAX          INTEGER {
                       eOff(1),
                      eOn(2)
               }   
   ACCESS           read-write    
   STATUS            optional   
   DESCRIPTION " Returns the current setting of the ePrint feature"
::= { settings-system2 20 }

-- 1.3.6.1.4.1.11.2.3.9.4.2.1.1.25.21   
eprint-email-address   OBJECT-TYPE
   SYNTAX          OCTET STRING   
   ACCESS           read-write    
   STATUS            optional   
   DESCRIPTION " This is the configured ePrint email address"
::= { settings-system2 21 }

-- 1.3.6.1.4.1.11.2.3.9.4.2.1.1.25.22   
eprint-email   OBJECT-TYPE
   SYNTAX          INTEGER {
                       eOff(1),
                      eOn(2)
               }   
   ACCESS           read-write    
   STATUS            optional   
   DESCRIPTION " This object reports the current setting of ePrint e-mail"
::= { settings-system2 22 }

-- 1.3.6.1.4.1.11.2.3.9.4.2.1.1.25.23   
eprint-printer-code   OBJECT-TYPE
   SYNTAX          OCTET STRING    
   ACCESS           read-write    
   STATUS            optional   
   DESCRIPTION " This is the configured ePrint printer code"
::= { settings-system2 23 }

-- 1.3.6.1.4.1.11.2.3.9.4.2.1.1.25.24   
eprint-hp-web-services   OBJECT-TYPE
   SYNTAX          INTEGER {
                       eOff(1),
                      eOn(2)
               }   
   ACCESS           read-write    
   STATUS            optional   
   DESCRIPTION " This object reports the current setting of the ePrint web
   services"
::= { settings-system2 24 }

-- 1.3.6.1.4.1.11.2.3.9.4.2.1.1.25.25   
eprint-jdi-interface   OBJECT-TYPE
   SYNTAX          INTEGER {
                       eJDIInterface1(1),
                      eJDIInterface2(2),
                      eJDIInterface3(3),
                      eJDIInterface4(4),
                      eJDIInterface5(5),
                      eJDIInterface6(6),
                      eJDIInterface7(7),
                      eJDIInterface8(8),
                      eJDIInterface9(9),
                      eJDIInterface10(10)
               }   
   ACCESS           read-write    
   STATUS            optional   
   DESCRIPTION " This number represents the instance of jdi that has ePrint
   registered"
::= { settings-system2 25 }

-- 1.3.6.1.4.1.11.2.3.9.4.2.1.1.25.31   
eprint-supported   OBJECT-TYPE
   SYNTAX          INTEGER {
                       eOff(1),
                      eOn(2)
               }   
   ACCESS           read-write    
   STATUS            optional   
   DESCRIPTION " This object is used to indicate whether the device supports
   ePrint or not. By default this should be eOff(1), but will be
   set to eOn(2) if the device supports ePrint"
::= { settings-system2 31 }

-- 1.3.6.1.4.1.11.2.3.9.4.2.1.1.25.32   
eprint-supported-jdi   OBJECT-TYPE
   SYNTAX          INTEGER {
                       eOff(1),
                      eOn(2)
               }   
   ACCESS           read-write    
   STATUS            optional   
   DESCRIPTION " This object is used to indicate whether the JDI supports ePrint
   or not. By default this should be eOff(1), but will be set to
   eOn(2) if JDI supports ePrint"
::= { settings-system2 32 }

-- 1.3.6.1.4.1.11.2.3.9.4.2.1.1.4.6.1.4   
web-proxy-config-enable   OBJECT-TYPE
   SYNTAX          INTEGER {
                       eOff(0),
                      eOn(1)
               }   
   ACCESS           read-only    
   STATUS            optional   
   DESCRIPTION " This object is a OCTET STRING enumeration which the peripheral uses
   to inform the JetDirect card that the Jet-Direct card embedded
   web server should display the web proxy configuration settings.
   The Jet Direct card web server will display the if and only if
   this object is both implemented and set to eOn. A peripheral
   may implement this object in order to have another host, like a
   JetDirect card, include a reference to the peripheral's web
   content. The peripheral will read the proxy configuration using
   the XIP2 sysInfo Get methods"
::= { settings-web-server 4 }

-- 1.3.6.1.4.1.11.2.3.9.4.2.1.1.4.3.1.4   
mio1-type   OBJECT-TYPE
   SYNTAX          INTEGER {
                       eEmpty(1),
                      eUnknown(2),
                      eUnSupported(3),
                      eReadOnlyMemory(4),
                      eVolatileRandomAccessMemory(5),
                      eNonVolatileRandomAccessMemory(6),
                      eFlashMemory(7),
                      eDiskDrive(8),
                      eRamRom(9),
                      eInputPHD(10),
                      eOutputPHD(11),
                      eIOCard(12),
                      eBindingPHD(13),
                      eSDRandomAccessMemory(14),
                      eSRandomAccessMemory(15),
                      eFPMRandomAccessMemory(16),
                      eEDORandomAccessMemory(17)
               }   
   ACCESS           read-only    
   STATUS            optional   
   DESCRIPTION " Returns an indication of the type of option installed in
   MIO/EIO slot 1. See SIMM1-TYPE for an explanation of the
   enumerations"
::= { mio1 4 }

-- 1.3.6.1.4.1.11.2.3.9.4.2.1.1.4.3.1.3   
mio1-manufacturing-info   OBJECT-TYPE
   SYNTAX          OCTET STRING    
   ACCESS           read-only    
   STATUS            optional   
   DESCRIPTION " Returns information describing the manufacture of the I/O card
   installed in MIO/EIO slot 1. May include serial number and
   firmware revision"
::= { mio1 3 }

-- 1.3.6.1.4.1.11.2.3.9.4.2.1.1.4.3.1.2   
mio1-model-name   OBJECT-TYPE
   SYNTAX          OCTET STRING    
   ACCESS           read-only    
   STATUS            optional   
   DESCRIPTION " Returns product information identifying the I/O card. Example:
   XXXX "
::= { mio1 2 }

-- 1.3.6.1.4.1.11.2.3.9.4.2.1.1.4.3.4.4   
mio4-type   OBJECT-TYPE
   SYNTAX          INTEGER {
                      eEmpty(1),
                      eUnknown(2),
                      eUnSupported(3),
                      eReadOnlyMemory(4),
                      eVolatileRandomAccessMemory(5),
                      eNonVolatileRandomAccessMemory(6),
                      eFlashMemory(7),
                      eDiskDrive(8),
                      eRamRom(9),
                      eInputPHD(10),
                      eOutputPHD(11),
                      eIOCard(12),
                      eBindingPHD(13),
                      eSDRandomAccessMemory(14),
                      eSRandomAccessMemory(15),
                      eFPMRandomAccessMemory(16),
                      eEDORandomAccessMemory(17)
               }   
   ACCESS           read-only    
   STATUS            optional   
   DESCRIPTION " Returns an indication of the type of option installed in
   MIO/EIO interface 4. See SIMM1-TYPE for an explanation of the
   enumerations"
::= { mio4 4 }

-- 1.3.6.1.4.1.11.2.3.9.4.2.1.1.4.3.4.3   
mio4-manufacturing-info   OBJECT-TYPE
   SYNTAX          OCTET STRING    
   ACCESS          read-only    
   STATUS          optional   
   DESCRIPTION " Returns information describing the manufacture of the I/O card
   installed in MIO/EIO interface 4. May include serial number and
   firmware revision"
::= { mio4 3 }

-- 1.3.6.1.4.1.11.2.3.9.4.2.1.1.25.59
set-primary-interface-index   OBJECT-TYPE
   SYNTAX          INTEGER    
   ACCESS           read-write    
   STATUS            optional   
   DESCRIPTION "Sets the index of the primary network interface to be used for outbound routing. Index 1 is EIO, 2 is wireless station, 3 is wireless access point and 4 is JDI."
::= { settings-system2 59 }


-- 1.3.6.1.4.1.11.2.3.9.4.2.1.1.4.3.4.2   
mio4-model-name   OBJECT-TYPE
   SYNTAX          OCTET STRING    
   ACCESS           read-only    
   STATUS            optional   
   DESCRIPTION " Returns product information identifying the I/O card. Example:
   XXXX"
::= { mio4 2 }


-- 1.3.6.1.4.1.11.2.3.9.4.2.1.1.25.60
wireless-direct-print-setting   OBJECT-TYPE
   SYNTAX          INTEGER {                       
                             eDisabled(1),                      
							 eEnabled(2)               
							 }   
   ACCESS           read-write    
   STATUS            optional   
   DESCRIPTION "Enable or disable wireless direct printing."
::= { settings-system2 60 }

-- 1.3.6.1.4.1.11.2.3.9.4.2.1.2.1.1.1   
io-timeout   OBJECT-TYPE
   SYNTAX          INTEGER    
   ACCESS           read-write    
   STATUS            optional   
   DESCRIPTION " The amount of time, in seconds, to wait for more print job data
   to be received before an I/O timeout occurs. The I/O channel
   being timed is the I/O channel that received the data
   associated with the current print job. If an I/O timeout
   occurs, the PDL processing sub-system assumes all the data
   associated with the current print job has been received, and
   processes the end of job in a PDL specific manner. The POS
   specifies the supported values"
::= { settings-io 1 }

-- 1.3.6.1.4.1.11.2.3.9.4.2.1.1.1.43   
direct-connect-ports-enable   OBJECT-TYPE
   SYNTAX          INTEGER {
                      eFalse(1),
                      eTrue(2),
                      eUnSupported(3)
               }   
   ACCESS           read-write    
   STATUS            optional   
   DESCRIPTION " This object specifies whether all direct connect ports
   (parallel and USB) are available or ignored. JetDirect,
   embedded network connectivity, and third party add-on cards
   (such as Firewire) will be unaffected by setting this object"
::= { settings-system 43 }

-- 1.3.6.1.4.1.11.2.3.9.4.2.1.1.4.9.2.5   
usb-product-id   OBJECT-TYPE
   SYNTAX          INTEGER    
   ACCESS           read-only    
   STATUS            optional   
   DESCRIPTION " Returns the Product ID of a connected USB device as defined in
   the Standard Device Descriptor of the Universal Serial Bus
   Specification Version 2   . The value will be in the range
   0..65535"
::= { usb 5 }

-- 1.3.6.1.4.1.11.2.3.9.4.2.1.1.4.9.2.4   
usb-vendor-id   OBJECT-TYPE
   SYNTAX          INTEGER    
   ACCESS           read-only    
   STATUS            optional   
   DESCRIPTION " Returns the Vendor ID of a connected USB device as defined in
   the Standard Device Descriptor of the Universal Serial Bus
   Specification Version 2   . The value will be in the range
   0..65535"
::= { usb 4 }

-- 1.3.6.1.4.1.11.2.3.9.4.2.1.2.1.1.2   
io-switch   OBJECT-TYPE
   SYNTAX          INTEGER {
                       eYes(1)
               }   
   ACCESS           read-only    
   STATUS            optional   
   DESCRIPTION " Indicates if the device will switch between I/O channels when a
   job boundary is encountered and print job data is available on
   another I/O channel"
::= { settings-io 2 }

-- 1.3.6.1.4.1.11.2.3.9.4.2.1.1.4.9.2.1. 
usb-serial-number   OBJECT-TYPE
   SYNTAX          OCTET STRING    
   ACCESS           read-only    
   STATUS            optional   
   DESCRIPTION " Returns the serial number of a connected USB device as defined
   in the Standard Device Descriptor of the Universal Serial Bus
   Specification Version 2"
::= { usb 1 }

-- 1.3.6.1.4.1.11.2.3.9.4.2.1.1.4.9.2.2. 
usb-manufacturer-name   OBJECT-TYPE
   SYNTAX          OCTET STRING    
   ACCESS           read-only    
   STATUS            optional   
   DESCRIPTION "Returns the description  of the manufacturer of a connected USB
   device as defined in the Standard Device Descriptor of the
   Universal Serial Bus Specification Version 2"
::= { usb 2 }

-- 1.3.6.1.4.1.11.2.3.9.4.2.1.1.4.9.2.3. 
usb-product-description   OBJECT-TYPE
   SYNTAX          OCTET STRING    
   ACCESS           read-only    
   STATUS            optional   
   DESCRIPTION "Returns the product description  of a connected USB device as
   defined in the Standard Device Descriptor of the Universal
   Serial Bus Specification Version 2"
::= { usb 3 }

-- 1.3.6.1.4.1.11.2.3.9.4.2.1.1.4.9.2.6. 
usb-device-kind   OBJECT-TYPE
   SYNTAX          INTEGER {
                       eUSBStorageDevice(1),
                      eUSBNonStorageDevice(2),
                      eUSBCompositeDevice(3),
                      eUSBUnsupportedDevice(4)
               }   
   ACCESS           read-only    
   STATUS            optional   
   DESCRIPTION " The USB-DEVICE-KIND object classifies a USB device into one of
   four broad categories: \ 
       eUSBStorageDevice(1): The USB device is strictly a device
   	for storing data. \ 
    eUSBNonStorageDevice(2): The USB device has no storage
    capability (e.g., a card reader). \ 
    eUSBCompositeDevice(3): The USB device has storage
    capability and additional functionality normally not
    associated with a storage device. \ 
    eUSBUnsupportedDevice(4): The USB device was detected, but no
    driver exists for the device or the device draws more current
    than allowed. \"
::= { usb 6 }

-- 1.3.6.1.4.1.11.2.3.9.4.2.1.1.4.9.2.7. 
usb-driver-name   OBJECT-TYPE
   SYNTAX          OCTET STRING    
   ACCESS           read-only    
   STATUS            optional   
   DESCRIPTION " Returns the name of the low-level USB driver supporting this device"
::= { usb 7 }

-- 1.3.6.1.4.1.11.2.3.9.4.2.1.1.4.9.1   
usb-host-supported   OBJECT-TYPE
   SYNTAX          INTEGER {
                       eFalse(1),
                      eTrue(2)
               }   
   ACCESS           read-only    
   STATUS            optional   
   DESCRIPTION " The USB Host protocol is supported by the device when the value
   returned is eTrue. The USB Host protocol is not supported when
   the value returned is eFalse"
::= { usb-interface 1 }

-- 1.3.6.1.4.1.11.2.3.9.4.2.1.1.3.5   
fw-rom-datecode   OBJECT-TYPE
   SYNTAX          OCTET STRING    
   ACCESS           read-only    
   STATUS            optional   
   DESCRIPTION " Identifies the base device-system firmware date code. The date code
   will be encoded in the yyyymmdd format. There may be several
   versions of the base device-system firmware. The date code associated
   with the version of the base device-system firmware that is being used
   is reported. There may be other date code objects for other
   specific modules such as fonts, localization modules, etc.;
   these other datecode objects are device specific"
::= { id 5 }

-- 1.3.6.1.4.1.11.2.3.9.4.2.1.1.3.6   
fw-rom-revision   OBJECT-TYPE
   SYNTAX          OCTET STRING    
   ACCESS           read-only    
   STATUS            optional   
   DESCRIPTION " This identifies the device-system code firmware ROM revision code. The
   format for a revision is major_revision.minor_revision. There
   may be other ROM revision code objects for other specific ROMs
   such as font ROMs, localization ROMs, etc; these other ROM
   revision code objects are device specific"
::= { id 6 }

-- 1.3.6.1.4.1.11.2.3.9.4.2.1.1.1.68   
factory-reset   OBJECT-TYPE
   SYNTAX          INTEGER    
   ACCESS           write-only    
   STATUS            optional   
   DESCRIPTION "writing an INTEGER 0 will do factory reset on system variables,
   MFP Settings and the .NET database without a reboot."
   ::= { settings-system 68 }

-- 1.3.6.1.4.1.11.2.3.9.4.2.1.1.16.1.5   
usage-instructions-line1   OBJECT-TYPE
   SYNTAX          OCTET STRING    
   ACCESS           read-write    
   STATUS            optional   
   DESCRIPTION " The first line of usage instructions for the device
   user.Appears on Line 1 of the usage page"
::= { printer-accounting 5 }

-- 1.3.6.1.4.1.11.2.3.9.4.2.1.1.16.1.6   
usage-instructions-line2   OBJECT-TYPE
   SYNTAX          OCTET STRING    
   ACCESS           read-write    
   STATUS            optional   
   DESCRIPTION " The second line of usage instructions for the device
   user.Appears on Line 1 of the usage page"
::= { printer-accounting 6 }

-- 1.3.6.1.4.1.11.2.3.9.4.2.1.1.16.1.7   
usage-instructions-line3   OBJECT-TYPE
   SYNTAX          OCTET STRING    
   ACCESS           read-write    
   STATUS            optional   
   DESCRIPTION " The third line of usage instructions for the device
   user.Appears on Line 1 of the usage page"
::= { printer-accounting 7 }

-- 1.3.6.1.4.1.11.2.3.9.4.2.1.1.16.1.8   
usage-instructions-line4   OBJECT-TYPE
   SYNTAX          OCTET STRING    
   ACCESS           read-write    
   STATUS            optional   
   DESCRIPTION " The fourth line of usage instructions for the device
   user.Appears on Line 1 of the usage page"
::= { printer-accounting 8 }

-- 1.3.6.1.4.1.11.2.3.9.4.2.1.1.6.1.10   
hold-job-timeout   OBJECT-TYPE
   SYNTAX          INTEGER    
   ACCESS           read-write    
   STATUS            optional   
   DESCRIPTION " The time, in minutes, that the printer will wait before
   automatically deleting a held job. This allows the printer to
   automatically clean up jobs that have been forgotten (held but
   never released)"
::= { settings-job 10 }

-- 1.3.6.1.4.1.11.2.3.9.4.2.1.1.6.7.1.1. 
held-job-user-name   OBJECT-TYPE
   SYNTAX          OCTET STRING    
   ACCESS           read-only    
   STATUS            optional   
   DESCRIPTION " User name that is obtained by the driver through some internal
   method or from user input"
::= { held-job-info 1 }

-- 1.3.6.1.4.1.11.2.3.9.4.2.1.1.6.7.1.2. 
held-job-job-name   OBJECT-TYPE
   SYNTAX          OCTET STRING    
   ACCESS           read-only    
   STATUS            optional   
   DESCRIPTION " The job name may be generated by the driver or obtained from
   user input"
::= { held-job-info 2 }

-- 1.3.6.1.4.1.11.2.3.9.4.2.1.1.6.7.1.3. 
held-job-retention   OBJECT-TYPE
   SYNTAX          INTEGER {
                       eHoldOff(1),
                      eHoldOn(2),
                      eHoldStore(3),
                      eHoldProof(4)
               }   
   ACCESS           read-only    
   STATUS            optional   
   DESCRIPTION " Indicates the retention classification of the job. The values
   indicate whether the job is printed immediately or stored.
   There are 4 options: \\ 
       eHoldOff: The job is printed but not retained on the disk.     \\ 
       eHoldOn: The job is printed and stored temporarily on the disk. \\ 
       eHoldStore: The job is not printed but stored on the disk.	\\ 
       eHoldProof: One copy of the job is printed and the
       remaining copies are stored on the disk. \\"
::= { held-job-info 3 }

-- 1.3.6.1.4.1.11.2.3.9.4.2.1.1.6.7.1.4. 
held-job-security   OBJECT-TYPE
   SYNTAX          INTEGER {
                       eHoldTypePublic(1),
                      eHoldTypePrivate(2)
               }   
   ACCESS           read-only    
   STATUS            optional   
   DESCRIPTION " The variable specifies the security level of the job. \\ 
       eHoldTypePublic: The job does not require a PIN in order to
   	release the job for printing. \\ 
       eHoldTypePrivate: The job requires a PIN in order to be
      released for printing. \\"
::= { held-job-info 4 }

-- 1.3.6.1.4.1.11.2.3.9.4.2.1.1.6.7.1.5. 
held-job-quantity   OBJECT-TYPE
   SYNTAX          INTEGER    
   ACCESS           read-only    
   STATUS            optional   
   DESCRIPTION " Number of copies to print"
::= { held-job-info 5 }

-- 1.3.6.1.4.1.11.2.3.9.4.2.1.1.6.7.1.6. 
held-job-pin   OBJECT-TYPE
   SYNTAX          OCTET STRING    
   ACCESS           read-only    
   STATUS            optional   
   DESCRIPTION " A OCTET STRING that is specified in the job stream and then required
   to be entered in order to release the job for printing. PIN
   stands for Personal Identification Number"
::= { held-job-info 6 }

-- 1.3.6.1.4.1.11.2.3.9.4.2.1.1.6.7.2.1   
held-job-print   OBJECT-TYPE
   SYNTAX          OCTET STRING    
   ACCESS           write-only    
   STATUS            optional   
   DESCRIPTION " Instructs the printer to schedule the specified held job for
   printing with the specified number of copies. The job-id is
   used to identify which job to print. A held job can also be
   printed from the control panel"
::= { held-job-control 1 }

-- 1.3.6.1.4.1.11.2.3.9.4.2.1.1.6.7.2.2   
held-job-delete   OBJECT-TYPE
   SYNTAX          INTEGER    
   ACCESS           write-only    
   STATUS            optional   
   DESCRIPTION " Instructs the printer to delete the specified held job from the
   list. The job-id is used to identify which job to delete. A
   held job can also be deleted from the control panel"
::= { held-job-control 2 }

-- 1.3.6.1.4.1.11.2.3.9.4.2.1.1.6.7.2.3   
held-job-set-queue-size   OBJECT-TYPE
   SYNTAX          INTEGER    
   ACCESS           read-write    
   STATUS            optional   
   DESCRIPTION " Sets the maximum number of jobs which can be stored in the held
   job list"
::= { held-job-control 3 }

-- 1.3.6.1.4.1.11.2.3.9.4.2.1.1.2.5   
on-off-line   OBJECT-TYPE
   SYNTAX          INTEGER {
                       eOnline(1),
                      eOffline(2),
                      eOfflineAtEndOfJob(3)
               }   
   ACCESS           read-write    
   STATUS            optional   
   DESCRIPTION " To bring the PDL processing sub-system on or off line. If the
   device is a printer, then the printer does not process print
   job data when the printer is off line. PML communication
   persists"
::= { status-system 5 }

-- 1.3.6.1.4.1.11.2.3.9.4.2.1.1.6.1.3   
job-info-change-id   OBJECT-TYPE
   SYNTAX          OCTET STRING    
   ACCESS           read-only    
   STATUS            optional   
   DESCRIPTION " Returns the current value of an object in the job-info sub-tree
   whose value has changed. Define the object identifier for the
   object whose value has changed as
   job-info.required-field.optional-field.job-id. job-info
   represents the OID prefix of all objects in the job-info
   sub-tree. Required-field represents the OID field value that
   follows the job-info prefix. Since some objects in the job-info
   sub-tree have two OID fields between the job-info prefix and
   the job-id, the optional-field represents the OID field between
   the required-field and the job-id field, if present. Using this
   definition, the format for the JOB-INFO-CHANGE-ID OCTET STRING value
   can be described as follows: \\ 
       Bytes 0-3 : required-field \\ 
       Bytes 4-7 : optional-field, or all zeros if there \\ 
       is no optional field \\ 
       Bytes 8-11: Job ID. \\ 
       Bytes 12-n : The value of the object job-info.
       required-field.optional-field.job-id. \\ 
      All multi-byte values stored in Motorola (big-endian) format,	
	where the most significant byte occurs first"
::= { settings-job 3 }

-- 1.3.6.1.4.1.11.2.3.9.4.2.1.1.6.1.2   
cancel-job   OBJECT-TYPE
   SYNTAX          INTEGER    
   ACCESS           read-write    
   STATUS            optional   
   DESCRIPTION " Cancels the print job whose ID matches the value written to the
   CANCEL-JOB object. The host first learns the job ID using the
   CURRENT-JOB-PARSING-ID command. If the printer has completely
   processed the job, the printer responds with
   <ErrorInvalidOrUnsupportedValue>. If the value of the
   CURRENT-JOB-PARSING-ID is smaller than the value written to the
   CANCEL-JOB object, then the printer responds with
   <ErrorInvalidOrUnsupportedValue>. When read, returns the value
   of the last job ID what was canceled, or -1 to indicate no job
   has been canceled"
::= { settings-job 2 }

-- 1.3.6.1.4.1.11.2.3.9.4.2.1.1.25.47
fax-init-at-command   OBJECT-TYPE
   SYNTAX          OCTET STRING    
   ACCESS           write-only    
   STATUS            optional   
   DESCRIPTION "This custom fax modem commands will be executed on the modem
   every time a fax modem is initialized along with the predefined
   set of commands
       "
::= { settings-system2 47 }

-- 1.3.6.1.4.1.11.2.3.9.4.2.1.2.2.1.83
scanner-accessory-digital-send-config-fax-embedded   OBJECT-TYPE
   SYNTAX          INTEGER    
   ACCESS           read-write    
   STATUS            optional   
   DESCRIPTION " Indicates if the analog fax device is available.
       "
::= { settings-scanner 83 }

-- 1.3.6.1.4.1.11.2.3.9.4.2.1.3.7.2.15
fax-notification-available   OBJECT-TYPE
   SYNTAX          INTEGER {                       
                                     eNotAvailable(1),                      
				     eAvailable(2)               }   
   ACCESS           read-only    
   STATUS            optional   
   DESCRIPTION "To check if the embedded Fax accessory or the Fax Service
   available on the device supports Notification for Faxes Sent
       "
::= { status-fax-proc-sub 15 }

-- 1.3.6.1.4.1.11.2.3.9.4.2.1.3.7.2.14
pcfax-send-operational   OBJECT-TYPE
   SYNTAX          INTEGER {                       
                                    eNonOperational(1),                      
				     eOperational(2)               }   
   ACCESS           read-only    
   STATUS            optional   
   DESCRIPTION "To check if a fax can be sent from a PC to the device. This
   checks if a Fax service is supported on the MFP and if the
   administrator has enabled PC Fax Send for the device.
   Additional return types may be supported later to indicate why
   PC Fax Send is not operational on the device
      "
::= { status-fax-proc-sub 14 }

-- 1.3.6.1.4.1.11.2.3.9.4.2.1.1.25.1   
toner-miser-plus-value   OBJECT-TYPE
   SYNTAX          OCTET STRING    
   ACCESS           write-only    
   STATUS            optional   
   DESCRIPTION " This object is used to enable/disable toner miser plus
   feature"
::= { settings-system2 1 }

-- 1.3.6.1.4.1.11.2.3.9.4.2.1.1.25.2   
toner-miser-plus-supported   OBJECT-TYPE
   SYNTAX          INTEGER {
                       eOff(1),
                      eOn(2)
               }   
   ACCESS           read-only    
   STATUS            optional   
   DESCRIPTION " The supported values are ON and OFF. The toner miser plus
   feature is turned OFF by default"
::= { settings-system2 2 }

-- 1.3.6.1.4.1.11.2.3.9.4.2.1.4.1.7.3.2.2   
phd2-device-specific-command   OBJECT-TYPE
   SYNTAX          OCTET STRING    
   ACCESS           write-only    
   STATUS            optional   
   DESCRIPTION " This object is used to send device-specific data to the paper
   handling device. The meaning of the device-specific command is
   dependent on the paper handling device and must be specified in
   the POS. If the paper handling device does not accept the
   command, then an <ErrorInvalidOrUnsupportedValue> will be
   returned. If the device accepts the command, it may still be
   processing the command after the response has been returned.
   Depending on the device, the application may need to query
   PHDx-DEVICE-MEMORY to see when the command has completed"
::= { ph2 2 }

-- 1.3.6.1.4.1.11.2.3.9.4.2.1.1.1.99   
start-engine-early-warmup   OBJECT-TYPE
   SYNTAX          INTEGER {
                       eValue1(1)
               }   
   ACCESS           write-only    
   STATUS            mandatory   
   DESCRIPTION " This PML object is used by HP SW drivers to signal the printer
   that a job is coming, and to start the warm-up process
   early.The effect of warming up early will reduce the First Page
   Out time"
::= { settings-system 99}

-- 1.3.6.1.4.1.11.2.3.9.4.2.1.1.1.101   
enable-engine-early-warmup   OBJECT-TYPE
   SYNTAX          INTEGER {
                      eDisable(1),
                      eEnable(2)
               }   
   ACCESS           read-write    
   STATUS            optional   
   DESCRIPTION " This PML object is used by HP SW to enable/disable the printer
   to send the signal of warm-up process early to engine. The
   effect of warming up early will reduce the First Page Out   time"
::= { settings-system 101 }

-- 1.3.6.1.4.1.11.2.3.9.4.2.1.4.1.1.5   
print-density   OBJECT-TYPE
   SYNTAX          INTEGER(0..10)    
   ACCESS           read-write    
   STATUS            optional   
   DESCRIPTION " Returns or sets the print density setting. Print density is the
   instantaneous amount of marking agent applied to the paper
   while printing. A value of zero has the lowest print density,
   yielding a lighter page. A value of 10 has the highest print
   density, yielding a darker page. Each POS should document what
   values in the 0 to 10 range are supported"
::= { settings-prt-eng 5 }

-- 1.3.6.1.4.1.11.2.3.9.4.2.1.1.3.20   
formatter-serial-number   OBJECT-TYPE
   SYNTAX          OCTET STRING    
   ACCESS           read-only    
   STATUS            optional   
   DESCRIPTION " This object returns the formatter serial number for the device.
   The value returned from this object is the FORMATTERNUMBER device-system variable. 
   If possible, encode the serial number in a
   symbol set (like Roman-8) that matches the ASCII character set
   and limit the characters used to ASCII characters"
::= { id 20 }

-- 1.3.6.1.4.1.11.2.3.9.4.2.1.4.1.3.1.2   
input-tray-auto-select   OBJECT-TYPE
   SYNTAX          INTEGER {
                       eOff(1),
                      eOn(2)
               }   
   ACCESS           read-write    
   STATUS            optional   
   DESCRIPTION " Indicates if the device will automatically try to load media
   from the next input media tray in the auto-select sequence
   (defined by each device) when it cannot load media from the
   current tray. Locked trays will not be permitted in the
   auto-select sequence. This object has no meaning if there is
   only one unlocked input media tray"
::= { settings-intray 2 }

-- 1.3.6.1.4.1.11.2.3.9.4.2.1.4.1.3.1.10   
default-custom-paper-dim-unit   OBJECT-TYPE
   SYNTAX          INTEGER {
                       eTenThousandthsOfInches(3),
                      eMicrometers(4)
               }   
   ACCESS           read-write    
   STATUS            optional   
   DESCRIPTION " The units of measure used to specify the width and height of
   the printer's default custom paper size. The unit of measure of
   eTenThousandthsOfInches is 0   001 inches"
::= { settings-intray 10 }

-- 1.3.6.1.4.1.11.2.3.9.4.2.1.1.4.5.2.2   
phd2-manufacturing-info   OBJECT-TYPE
   SYNTAX          OCTET STRING    
   ACCESS           read-only    
   STATUS            optional   
   DESCRIPTION " Returns information describing the manufacture of PHD 2. May
   include serial number and firmware revision"
::= { phd2 2 }

-- 1.3.6.1.4.1.11.2.3.9.4.2.1.1.4.5.2.1   
phd2-model   OBJECT-TYPE
   SYNTAX          OCTET STRING    
   ACCESS           read-only    
   STATUS            optional   
   DESCRIPTION " Returns product information identifying PHD device 2. Example:
   XXXX"
::= { phd2 1 }

-- 1.3.6.1.4.1.11.2.3.9.4.2.1.1.4.5.2.4   
phd2-capacity   OBJECT-TYPE
   SYNTAX          INTEGER    
   ACCESS           read-only    
   STATUS            optional   
   DESCRIPTION " Returns an indication of the capacity of the installed option.
   See SIMM1-CAPACITY for an explanation of the meaning of the
   value of this object"
::= { phd2 4 }

-- 1.3.6.1.4.1.11.2.3.9.4.2.1.1.4.5.2.3   
phd2-type   OBJECT-TYPE
   SYNTAX          INTEGER {
                       eEmpty(1),
                      eUnknown(2),
                      eUnSupported(3),
                      eReadOnlyMemory(4),
                      eVolatileRandomAccessMemory(5),
                      eNonVolatileRandomAccessMemory(6),
                      eFlashMemory(7),
                      eDiskDrive(8),
                      eRamRom(9),
                      eInputPHD(10),
                      eOutputPHD(11),
                      eIOCard(12),
                      eBindingPHD(13),
                      eSDRandomAccessMemory(14),
                      eSRandomAccessMemory(15),
                      eFPMRandomAccessMemory(16),
                      eEDORandomAccessMemory(17)
               }   
   ACCESS           read-only    
   STATUS            optional   
   DESCRIPTION " Returns an indication of the type of option installed in PHD
   interface 2. See SIMM1-TYPE for an explanation of the
   enumerations"
::= { phd2 3 }

-- 1.3.6.1.4.1.11.2.3.9.4.2.1.1.1.97   
large-size-media-default-grain-direction   OBJECT-TYPE
   SYNTAX          INTEGER {
                       eShortGrain(1),
                      eLongGrain(2)
               }   
   ACCESS           read-write    
   STATUS            optional   
   DESCRIPTION " This object identifies default grain direction for large size
   media (B/A3) only. Default value is eShortGrain"
::= { settings-system 97 }

-- 1.3.6.1.4.1.11.2.3.9.4.2.1.1.4.5.2.5   
phd2-number-of-options   OBJECT-TYPE
   SYNTAX          INTEGER    
   ACCESS           read-only    
   STATUS            optional   
   DESCRIPTION "This object will return the number of finishing options
   supported by this object.    
   interaction For each option supported, there will be a corresponding sub
   array object for the PHD2-OPTIONS-MODEL and
   PHD2-OPTIONS-DESCRIPTION."
::= { phd2 5 }

-- 1.3.6.1.4.1.11.2.3.9.4.2.1.1.4.5.2.6. 
phd2-options-model   OBJECT-TYPE
   SYNTAX          OCTET STRING    
   ACCESS           read-only    
   STATUS            optional   
   DESCRIPTION "If the external paper handling device (PHD) supports at least
   one (1) finishing option, then this object will exist,
   otherwise ERROR-UNKNOWN-OBJECT-IDENTIFIER should be returned.
   Each finishing object supported by the PHD will be represented
   by a different sub-array element. The sub-array element returns
   the MODEL NUMBER of the finishing option supported, such as
   Booklet Making or Punching. This may be in the form of C115997
   or other types of model numbers.    INTERACTION For each sub-array element, there is a corresponding element in
   the PHD2-OPTIONS-DESCRIPTION object. See the
   PHD2-OPTIONS-DESCRIPTION object description for more information"
::= { phd2 6 }

-- 1.3.6.1.4.1.11.2.3.9.4.2.1.1.4.5.2.7. 
phd2-options-description   OBJECT-TYPE
   SYNTAX          OCTET STRING    
   ACCESS           read-only    
   STATUS            optional   
   DESCRIPTION "If the external paper handling device (PHD) supports at least
   one (1) finishing option, then this object will exist,
   otherwise ERROR-UNKNOWN-OBJECT-IDENTIFIER should be returned.
   Each finishing object supported by the PHD will be represented
   by a different sub-array element. The sub-array element returns
   a description of the finishing option supported, such as
   Booklet Making or Punching.    INTERACTION :For each sub-array element, there is a corresponding element in
   the PHD2-OPTIONS-MODEL object. See the PHD2-OPTIONS-MODEL
   object description for more information"
::= { phd2 7 }

-- 1.3.6.1.4.1.11.2.3.9.4.2.1.4.1.4.1.4   
overflow-bin   OBJECT-TYPE
   SYNTAX          INTEGER    
   ACCESS           read-write    
   STATUS            optional   
   DESCRIPTION " Returns or sets the bin that will be used for additional sheets
   of media when the current bin is full and printing is allowed
   to continue"
::= { settings-outbin 4 }

-- 1.3.6.1.4.1.11.2.3.9.4.2.1.1.1.32.12   
device-configure-printer-parameters   OBJECT-TYPE
   SYNTAX          OCTET STRING    
   ACCESS           read-write    
   STATUS            optional   
   DESCRIPTION " Allow the printer to be configured as a duplex or simplex
   printer. There will be a <<hidden>> encoded in this string and
   decoded by the printer firmware. If the <<hidden>> check passes
   the printer will be configured accordingly"
::= { device-configure 12 }

-- 1.3.6.1.4.1.11.2.3.9.4.2.1.1.5.7   
engine-self-diagnostic   OBJECT-TYPE
   SYNTAX          OCTET STRING    
   ACCESS           read-only    
   STATUS            optional   
   DESCRIPTION " The ENGINE-SELF-DIAGNOSTIC object reveals current engine
   failures; it returns a OCTET STRING string of two-byte motor, clutch,
   solenoid, and sensor failure codes"
::= { test 7 }

-- 1.3.6.1.4.1.11.2.3.9.4.2.1.1.5.8   
engine-parameter   OBJECT-TYPE
   SYNTAX          OCTET STRING    
   ACCESS           read-only    
   STATUS            optional   
   DESCRIPTION " The ENGINE-PARAMETER object returns a device specific set of
   engine parameters as a OCTET STRING string of byte values. It will be
   necessary to have a decoder for each engine to interpret the
   data"
::= { test 8 }

-- 1.3.6.1.4.1.11.2.3.9.4.2.1.1.4.5.3.2   
phd3-manufacturing-info   OBJECT-TYPE
   SYNTAX          OCTET STRING    
   ACCESS           read-only    
   STATUS            optional   
   DESCRIPTION " Returns information describing the manufacture of PHD 3. May
   include serial number and firmware revision"
::= { phd3 2 }

-- 1.3.6.1.4.1.11.2.3.9.4.2.1.1.4.5.3.1   
phd3-model   OBJECT-TYPE
   SYNTAX          OCTET STRING    
   ACCESS           read-only    
   STATUS            optional   
   DESCRIPTION " Returns product information identifying PHD device 3. Example:
   XXXX"
::= { phd3 1 }

-- 1.3.6.1.4.1.11.2.3.9.4.2.1.1.4.5.3.4   
phd3-capacity   OBJECT-TYPE
   SYNTAX          INTEGER    
   ACCESS           read-only    
   STATUS            optional   
   DESCRIPTION " Returns an indication of the capacity of the installed option.
   See SIMM1-CAPACITY for an explanation of the meaning of the
   value of this object"
::= { phd3 4 }

-- 1.3.6.1.4.1.11.2.3.9.4.2.1.1.4.5.3.3   
phd3-type   OBJECT-TYPE
   SYNTAX          INTEGER {
                       eEmpty(1),
                      eUnknown(2),
                      eUnSupported(3),
                      eReadOnlyMemory(4),
                      eVolatileRandomAccessMemory(5),
                      eNonVolatileRandomAccessMemory(6),
                      eFlashMemory(7),
                      eDiskDrive(8),
                      eRamRom(9),
                      eInputPHD(10),
                      eOutputPHD(11),
                      eIOCard(12),
                      eBindingPHD(13),
                      eSDRandomAccessMemory(14),
                      eSRandomAccessMemory(15),
                      eFPMRandomAccessMemory(16),
                      eEDORandomAccessMemory(17)
               }   
   ACCESS           read-only    
   STATUS            optional   
   DESCRIPTION " Returns an indication of the type of option installed in PHD
   interface 3. See SIMM1-TYPE for an explanation of the
   enumerations"
::= { phd3 3 }

-- 1.3.6.1.4.1.11.2.3.9.4.2.1.1.4.5.3.5   
phd3-number-of-options   OBJECT-TYPE
   SYNTAX          INTEGER    
   ACCESS           read-only    
   STATUS            optional   
   DESCRIPTION "This object will return the number of finishing options
   supported by this object.   INTERACTION :For each option supported, there will be a corresponding sub
   array object for the PHD3-OPTIONS-MODEL and
   PHD3-OPTIONS-DESCRIPTION"
::= { phd3 5 }

-- 1.3.6.1.4.1.11.2.3.9.4.2.1.1.4.5.3.6. 
phd3-options-model   OBJECT-TYPE
   SYNTAX          OCTET STRING    
   ACCESS           read-only    
   STATUS            optional   
   DESCRIPTION "If the external paper handling device (PHD) supports at least
   one (1) finishing option, then this object will exist,
   otherwise ERROR-UNKNOWN-OBJECT-IDENTIFIER should be returned.
   Each finishing object supported by the PHD will be represented
   by a different sub-array element. The sub-array element returns
   the MODEL NUMBER of the finishing option supported, such as
   Booklet Making or Punching. This may be in the form of C115997
   or other types of model numbers.    INTERACTION For each sub-array element, there is a corresponding element in
   the PHD3-OPTIONS-DESCRIPTION object. See the
   PHD3-OPTIONS-DESCRIPTION object 
   description  for more information"
::= { phd3 6 }

-- 1.3.6.1.4.1.11.2.3.9.4.2.1.1.4.5.3.7. 
phd3-options-description   OBJECT-TYPE
   SYNTAX          OCTET STRING    
   ACCESS           read-only    
   STATUS            optional   
   DESCRIPTION "If the external paper handling device (PHD) supports at least
   one (1) finishing option, then this object will exist,
   otherwise ERROR-UNKNOWN-OBJECT-IDENTIFIER should be returned.
   Each finishing object supported by the PHD will be represented
   by a different sub-array element. The sub-array element returns
   a description of the finishing option supported, such as
   Booklet Making or Punching.    INTERACTION For each sub-array element, there is a corresponding element in
   the PHD3-OPTIONS-MODEL object. See the PHD3-OPTIONS-MODEL
   object description  for more information"
::= { phd3 7 }

-- 1.3.6.1.4.1.11.2.3.9.4.2.1.4.1.3.1.19   
tray-prompt   OBJECT-TYPE
   SYNTAX          INTEGER {
                       eDoNotDisplay(1),
                      eDisplay(2)
               }   
   ACCESS           read-write    
   STATUS            optional   
   DESCRIPTION " If this object is set to eDisplay, whenever a paper tray is
   opened, refilled, and closed in a printer, the end user is
   prompted with a message 'To change size or type press check' on
   the control panel. If this object is set to eDoNotDisplay, then
   the end user will not be prompted with this message whenever a
   paper tray is opened, refilled, and closed in a printer"
::= { settings-intray 19 }

-- 1.3.6.1.4.1.11.2.3.9.4.2.1.1.2.35   
job-input-auto-continue-timeout   OBJECT-TYPE
   SYNTAX          INTEGER    
   ACCESS           read-write    
   STATUS            optional   
   DESCRIPTION " The number of seconds the device waits after a job related
   continuable error occurs before automatically continuing. An
   example job related continuable error is the job requesting a
   media size that is not available. After the timeout expires,
   the device will continue processing the job as if a continue
   event occurred, such as the front panel continue key being
   pressed. If the value is -1, the device does not automatically
   continue after a job related continuable error occurs. If the
   value is 0, the device immediately continues. If the value is
   greater than 0, the value represents the timeout value in
   seconds"
::= { status-system 35 }

-- 1.3.6.1.4.1.11.2.3.9.4.2.1.1.2.36   
job-input-auto-continue-mode   OBJECT-TYPE
   SYNTAX          INTEGER {
                       cCancelJob(0),
                      cAutoMediaSizeOverride(1),
                      cAutoMediaNameOverride(2),
                      cUSMediaSizeOverride(3),
                      cISOMediaSizeOverride(4)
               }   
   ACCESS           read-write    
   STATUS            optional   
   DESCRIPTION " Returns or sets the device behavior when the desired media is
   not currently available. \\ 
       cCancelJob - The device cancels the job. The device POS
   	should explain what happens if this item is not the
	only item in the INTEGER. \\ 
    cAutoMediaSizeOverride - The device is allowed to
	substitute a different size media. \\ 
    cAutoMediaNameOverride - The device is allowed to
	substitute a different media name. \\ 
    cUSMediaSizeOverride - The device is allowed to substitute
	US media sizes (letter, etc.) for ISO media sizes (A4,	etc.). \\ 
    cISOMediaSizeOverride - The device is allowed to substitute
	ISO media sizes (A4, etc.) for US media sizes (letter,	etc.). \\"
::= { status-system 36 }

-- 1.3.6.1.4.1.11.2.3.9.4.2.1.1.2.40   
job-output-auto-continue-timeout   OBJECT-TYPE
   SYNTAX          INTEGER(-1..32767)    
   ACCESS           read-write    
   STATUS            optional   
   DESCRIPTION " Returns or sets the time that the printer will wait after an
   output bin becomes full and the printer is trying to deliver a
   sheet of media to that output bin. When the timeout expires,
   the job is processed according to the OUTBINn-OVERRIDE-MODE. A
   value of -1 indicates that the printer will wait for a continue
   event. A non-negative value is the number of seconds to wait"
::= { status-system 40 }

-- 1.3.6.1.4.1.11.2.3.9.4.2.1.4.1.1.28   
duplex-blank-pages   OBJECT-TYPE
   SYNTAX          INTEGER {
                       eDuplexBlankPagesAuto(1),
                      eDuplexBlankPagesYes(2)
               }   
   ACCESS           read-write    
   STATUS            optional   
   DESCRIPTION " When the value of the device-system variable is set to
   eDuplexBlankPagesAuto, it means to Smart Duplex in any of the
   specified conditions. This selection is logically equivalent to
   'NO, do not duplex blank pages if not duplexing them obtains a
   performance enhancement'. When the value of the device-system variable
   is set to eDuplexBlankPagesYes, it means to disable Smart
   Duplexing"
::= { settings-prt-eng 28 }

-- 1.3.6.1.4.1.11.2.3.9.4.2.1.1.1.31   
mono-color-switching-mode   OBJECT-TYPE
   SYNTAX          INTEGER{
                       eNeverSwitch(1),
                      eAlwaysSwitch(2),
                      eLookAheadSwitch(3)
               }   
   ACCESS           read-write    
   STATUS            optional   
   DESCRIPTION " This object allows the user to view/change the color/mono
   switching mode for a device"
::= { settings-system 31 }

-- 1.3.6.1.4.1.11.2.3.9.4.2.1.4.1.7.1.1   
tray-disable-use-instead    OBJECT-TYPE
   SYNTAX          INTEGER {
                       eDisabled(1),
                      eEnabled(2)
               }   
   ACCESS           read-write    
   STATUS            optional   
   DESCRIPTION " If this object is set to eEnabled, the paper mount message that
   is normally posted('To use another tray....') is turned off
   thereby disallowing the user to specify another tray from which
   paper can be taken for printing. However, on setting this
   object to eDisabled the paper mount message is posted allowing
   the user to specify another tray for paper feed"
::= { settings-ph 1 }


-- 1.3.6.1.4.1.11.2.3.9.4.2.1.4.1.3.3.1.24.
tray1-misprint-behavior-setting   OBJECT-TYPE
   SYNTAX          INTEGER {                       
                                  eNormalBehavior(1),                      
								  eClassicBehavior(2)               
								  }   
   ACCESS           read-write    
   STATUS            optional   
   DESCRIPTION "This object allows one to get/set the setting of the MISPRINT BEHAVIOR SETTING for Tray 1.This controls whether the classic misprint behavior is enabled"
::= { intray1 24 }



-- 1.3.6.1.4.1.11.2.3.9.4.2.1.3.3.1.36   
reprint   OBJECT-TYPE
   SYNTAX          INTEGER {
                       eOff(1),
                      eOn(2),
                      eAuto(3)
               }   
   ACCESS           read-write    
   STATUS            optional   
   DESCRIPTION " Returns or changes the reprint (jam recovery) setting. If eOn,
   then the device will reprint pages jammed pages. If eOff, the
   device will not attempt to reprint jammed pages. If eAuto, a
   device dependent algorithm (which should be documented in the
   POS) will be used to determine if the page gets reprinted. This
   object controls all PDLs, unless a specific PDL supports its
   own reprint control mechanism. To date, only PostScript has a
   PDL reprint control mechanism"
::= { settings-pdl 36 }

-- 1.3.6.1.4.1.11.2.3.9.4.2.1.4.1.2.26   
print-engine-revision   OBJECT-TYPE
   SYNTAX          OCTET STRING    
   ACCESS           read-only    
   STATUS            optional   
   DESCRIPTION " Print engine revision string"
::= { status-prt-eng 26 }

-- 1.3.6.1.4.1.11.2.3.9.4.2.1.4.1.3.1.11   
default-custom-paper-feed-dim   OBJECT-TYPE
   SYNTAX          INTEGER    
   ACCESS           read-write    
   STATUS            optional   
   DESCRIPTION " Sets the printer's default custom paper size dimension in the
   feed direction (direction parallel to the direction of paper
   feeding). The value for this object is specified in micrometers
   or tenthousandths of an inch, depending upon the value of
   DEFAULT-CUSTOM-PAPER-DIM-UNIT. The valid range is
   engine-dependent and should be documented in the POS for each
   product"
::= { settings-intray 11 }

-- 1.3.6.1.4.1.11.2.3.9.4.2.1.4.1.3.1.12   
default-custom-paper-xfeed-dim   OBJECT-TYPE
   SYNTAX          INTEGER    
   ACCESS           read-write    
   STATUS            optional   
   DESCRIPTION " Sets the printer's default custom paper size dimension in the
   cross-feed direction (direction ninety degrees relative to the
   direction of paper feeding). The value for this object is
   specified in micrometers or tenthousandths of an inch,
   depending upon the value of DEFAULT-CUSTOM-PAPER-DIM-UNIT. The
   valid range is engine-dependent and should be documented in the
   POS for each product"
::= { settings-intray 12 }

-- 1.3.6.1.4.1.11.2.3.9.4.2.1.4.1.3.1.14. 
input-tray-max-media-feed-dim   OBJECT-TYPE
   SYNTAX          INTEGER    
   ACCESS           read-only    
   STATUS            optional   
   DESCRIPTION " The maximum physical media size in the feed direction of this
   input device expressed in units of measure specified by INPUT-
   TRAY-MIN-MAX-DIM-UNIT. A value of (-1) implies 'unlimited', a
   value of (-2) implies 'unknown'"
::= { settings-intray 14 }

-- 1.3.6.1.4.1.11.2.3.9.4.2.1.4.1.3.1.15. 
input-tray-max-media-xfeed-dim   OBJECT-TYPE
   SYNTAX          INTEGER    
   ACCESS           read-only    
   STATUS            optional   
   DESCRIPTION " The maximum physical media size across the feed direction of a
   particular input device expressed in units of measure specified
   by INPUT-TRAY-MIN-MAX-DIM-UNIT. A value of (-1) implies
   'unlimited', a value of (-2) implies 'unknown'"
::= { settings-intray 15 }

-- 1.3.6.1.4.1.11.2.3.9.4.2.1.4.1.3.1.16. 
input-tray-min-media-feed-dim   OBJECT-TYPE
   SYNTAX          INTEGER    
   ACCESS           read-only    
   STATUS            optional   
   DESCRIPTION " The minimum physical media size in the feed direction of a
   particular input device expressed in units of measure specified
   by PrtInputMinMaxDimUnit. A value of (-1) implies 'unlimited',
   a value of (-2) implies 'unknown'"
::= { settings-intray 16 }

-- 1.3.6.1.4.1.11.2.3.9.4.2.1.4.1.3.1.17. 
input-tray-min-media-xfeed-dim   OBJECT-TYPE
   SYNTAX          INTEGER    
   ACCESS           read-only    
   STATUS            optional   
   DESCRIPTION " The minimum physical media size across the feed direction of a
   particular input device expressed in units of measure specified
   by PrtInputMinMaxDimUnit. A value of (-1) implies 'unlimited',
   a value of (-2) implies 'unknown'"
::= { settings-intray 17 }

-- 1.3.6.1.4.1.11.2.3.9.4.2.1.1.2.42   
collated-originals-support   OBJECT-TYPE
   SYNTAX          INTEGER {
                       cCollatedOriginals(0),
                      cProofAndHold(1),
                      cSecurityPrint(2),
                      cAutoHighlight(3),
                      cCollatedAtSpeed(4)
               }   
   ACCESS           read-only    
   STATUS            optional   
   DESCRIPTION " Indicates that the printer can create multiple, collated
   'originals' of a job and shows the level of support for this
   capability. \\ 
       cCollatedOriginals - The printer can create multiple
   	collated originals, or 'mopies'. This is the base
	functionality required by the other INTEGER items.		\\ 
    cProofAndHold - The printer saves a copy of the job while
	printing the first mopy. Later, this held job can be
	released and the rest of the mopies will print. \\ 
    cSecurityPrint - The printer spools the job and holds the
	job until the user releases the job by entering a
	<<hidden>> at the printer's control panel. \\ 
    cAutoHighlight - The printer prints the job a number of
	times with a mail distribution list prepended to each
	job. A different mailing address is highlighted on each mopy. \\ 
    cCollatedAtSpeed - The printer can create multiple collated
	copies where all copies after the original are printed
        at engine speed. \\ "
::= { status-system 42 }

-- 1.3.6.1.4.1.11.2.3.9.4.2.1.4.1.10.9   
device-used-while-cartridge-out-override-active   OBJECT-TYPE
   SYNTAX          INTEGER {
                       eNotUsed(1),
                      eUsed(2)
               }   
   ACCESS           read-only    
   STATUS            optional   
   DESCRIPTION " Returns eUsed if the device has ever been used while Cartridge
   Out Override is activated. Merely enabling cartridge out
   override will not cause eUsed to be returned. Cartridge Out
   Override must be activated by a cartridge becoming out and
   device must be used in that mode"
::= { consumables 9 }

-- 1.3.6.1.4.1.11.2.3.9.4.2.1.4.1.1.37   
cartridge-adaptive-gain-reset   OBJECT-TYPE
   SYNTAX          INTEGER {
                       eFalse(1),
                      eTrue(2)
               }   
   ACCESS           write-only    
   STATUS            optional   
   DESCRIPTION " This object will Reset the Adaptive TA Gain value to 1   0 and
   disable the adaptive TA routine. The value that this object
   returns is stored in non-volatile memory"
::= { settings-prt-eng 37 }

-- 1.3.6.1.4.1.11.2.3.9.4.2.1.4.1.10.5.2   
supplies-at-very-low-delay   OBJECT-TYPE
   SYNTAX           INTEGER {
                       eDisabled(1),
                      eEnabled(2)
               }   
   ACCESS            read-write    
   STATUS            optional   
   DESCRIPTION " Indicates if the transition to a VERY LOW state should be
   delayed by the number of pages specified in
   SUPPLIES-AT-VERY-LOW-DELAY-LIMIT"
::= { consumables-status 2 }

-- 1.3.6.1.4.1.11.2.3.9.4.2.1.4.1.1.38. 
supplies-at-very-low-setting   OBJECT-TYPE
   SYNTAX          INTEGER {
                       eStopAtOut(2),
                      eOverrideAtOut(4),
                      ePromptAtOut(6),
                      ePrintBlack(7)
               }   
   ACCESS           read-write    
   STATUS            optional   
   DESCRIPTION " This object can be used to change the setting of menu item AT
   VERY LOW. The behavior of the printer when a supply reaches low
   changes in accordance with the setting of this PML Object. If
   the option eStopAtOut is selected then printer will stop when a
   supply reaches Estimated End of Life (EEOL). If the option
   eOverrideAtOut is selected then printer will continue past EEOL
   in override mode. If the option eOverrideAtOut is selected then
   printer will continue past EEOL in override mode. If the option
   ePromptAtOut is selected then printer will ask the user if they
   wish to continue printing past EEOL in override mode. If the
   option eAutoContinueBlack is selected then printer will
   continue printing in mono past EEOL. This may be subject to
   page limits. (Color only) NOTE: This object replaces
   SUPPLIES-REPLACE-ACTION-AT-SETTING"
::= { settings-prt-eng 38 }

-- 1.3.6.1.4.1.11.2.3.9.4.2.1.4.1.10.5.1.3. 
consumable-life-low-threshold   OBJECT-TYPE
   SYNTAX          INTEGER    
   ACCESS           read-write    
   STATUS            optional   
   DESCRIPTION " This object is used to report and modify a threshold value
   indicating the point in the life of a consumable or supply at
   which a transition to a LOW state will occur"
::= { consumables-life 3 }

-- 1.3.6.1.4.1.11.2.3.9.4.2.1.4.1.10.5.1.6. 
supplies-at-very-low-delay-limit   OBJECT-TYPE
   SYNTAX           INTEGER    
   ACCESS            read-write    
   STATUS            optional   
   DESCRIPTION " This object is used to report and modify a very low delay limit
   value indicating the number of pages to delay the transition to
   a very low state for a supply."
::= { consumables-life 6 }

-- 1.3.6.1.4.1.11.2.3.9.4.2.1.4.1.1.36   
cartridge-adaptive-gain   OBJECT-TYPE
   SYNTAX          INTEGER   
   ACCESS           read-only    
   STATUS            optional   
   DESCRIPTION " The Adaptive TA Gain is stored for the last 5 cartridges.
   Cartridge one is the most recent to be installed (current), and
   cartridge 5 is least recent to be installed. This object is
   double array object. OID extension is
   CARTRIDGE-ADAPTIVE-GAIN.x.n, where x is 1..4 (x is Black, Cyan,
   Magenta, Yellow Toner), and n is 1..5 (n is number of cartridges) "
::= { settings-prt-eng 36 }

-- 1.3.6.1.4.1.11.2.3.9.4.2.1.4.1.10.15. 
total-kilo-pixels-per-cartridge   OBJECT-TYPE
   SYNTAX          INTEGER    
   ACCESS           read-only    
   STATUS            optional   
   DESCRIPTION " Returns the total number of kilo-pixels at 600dpi in the
   cartridge. That is, the number returned by this object should
   be multiplied by 1000 to determine the total number of pixels
   at 600dpi in the cartridge "
::= { consumables 15 }

-- 1.3.6.1.4.1.11.2.3.9.4.2.1.4.1.10.5.1.1. 
consumable-life-usage-units-remaining   OBJECT-TYPE
   SYNTAX          INTEGER    
   ACCESS           read-only    
   STATUS            optional   
   DESCRIPTION " This object reports the current estimate of the number of usage
   units that remain before this supply is depleted. An installed
   supply that cannot report such a number will return a value of
   -2. It is the reponsibility of the host application to query
   each supply in order to determine an overall device
   USAGE-UNITS-REMAINING number - the lowest value returned. The
   unit of measure for this life estimate is determined by reading
   the corresponding CONSUMABLE-LIFE-USAGE-UNITS object"
::= { consumables-life 1 }

-- 1.3.6.1.4.1.11.2.3.9.4.2.1.4.1.10.5.1.2. 
consumable-life-usage-units   OBJECT-TYPE
   SYNTAX          INTEGER {
                       ePagesRemaining(1),
                      eEstimatedPagesRemaining(2),
                      eUnknownUnits(3),
                      ePagesSinceLow(4),
                      ePagesSinceOut(5),
                      ePagesPicked(6),
                      ePercentLifeRemaining(7),
                      e4X6ImagesPrinted(8),
                      eEngineDropCount(9),
                      eEngineWebAdvances(10)
               }   
   ACCESS           read-only    
   STATUS            optional   
   DESCRIPTION " This object reports current usage units in use by the
   corresponding CONSUMABLE-LIFE-USAGE-UNITS-REMAINING object"
::= { consumables-life 2 }

-- 1.3.6.1.4.1.11.2.3.9.4.2.1.4.1.10.5.1.4. 
estimated-page-yield   OBJECT-TYPE
   SYNTAX          INTEGER    
   ACCESS           read-only    
   STATUS            optional   
   DESCRIPTION " Returns the estimated yield of the cartridge in
   ESTIMATED-PAGE-YIELD-UNIT units"
::= { consumables-life 4 }

-- 1.3.6.1.4.1.11.2.3.9.4.2.1.4.1.10.5.1.5. 
estimated-page-yield-unit   OBJECT-TYPE
   SYNTAX          INTEGER {
                       e5PercentPages(1),
                      eISOPages(2)
               }   
   ACCESS           read-only    
   STATUS            optional   
   DESCRIPTION " Returns the unit used for ESTIMATED-PAGE-YIELD"
::= { consumables-life 5 }

-- 1.3.6.1.4.1.11.2.3.9.4.2.1.4.1.10.7. 
consumable-current-state   OBJECT-TYPE
   SYNTAX          INTEGER {
                       cAuthLevel1(0),
                      cAuthLevel2(1),
                      cAuthLevel3(2),
                      cAuthLevel4(3),
                      cAuthLevel5(4),
                      cAuthLevel6(5),
                      cAuthLevel7(6),
                      cGenuineHPUnsupported(8),
                      cELabelDefective(9),
                      cELabelMissing(10),
                      cLowCondition(11),
                      cOutCondition(12),
                      cIncorrect(13),
                      cMissing(14),
                      cPastOutCondition(15), 
                      cConfigurableLow(16),
                      cExpired(17),
                      cFailure(18),
                      cLeak(19),
                      cUnknownManufacturer(20),
                      cUnsupported(21),
                      cUnavailable(22),
                      cIncompatible(23),
                      cStatusAreValid(31)
               }   
   ACCESS           read-only    
   STATUS            optional   
   DESCRIPTION " This PML object returns the current state of the particular
   consumable. \\ 
       cAuthLevel1 - Consumable is at Authentication Level 1 \\ 
       cAuthLevel2 - Consumable is at Authentication Level 2 \\ 
       cAuthLevel3 - Consumable is at Authentication Level 3 \\ 
       cAuthLevel4 - Consumable is at Authentication Level 4 \\ 
       cAuthLevel5 - Consumable is at Authentication Level 5 \\ 
       cGenuineHPUnsupported - Cartridge is GenuineHP intended for another product \\ 
    cDefectiveMemory - Cartridge has a defective memory tag \\ 
    cMissingMemory - Memory tag is missing from the cartridge\\ 
    cLowCondition - Consumable has reached the engine low threshold \\ 
    cOutCondition - Consumable has reached its out threshold \\ 
    cIncorrect - Cartridge inserted is not the correct one \\ 
    cMissing - Consumable is missing from the printer \\ 
    cConfigurableLow - Consumable has reached the configurable low threshold value \\ 
    cStatusArevalid - The status reported on other bits are
	valid only if the bit is set to 1. If it is 0, the values are invalid. \\ 
    cExpired - Is the cartridge expired, which is determined \\ 
	    by the formatter.\\ 
    cFailure - Cartridge has failed determined by the engine. \\ 
    cLeak - Cartridge has a leak as determined by the engine. \\ 
    cUnknownManufacturer - the brand of the cartridge is \\ 
    unknown as determined by the engine. \\ 
    cUnsupported --- Cartridge is not supported as determined\\ 
		    by the engine. \\ 
    cIncompatible - When installed consumable is incompatible with
	current printer. These are the possible states and whenever the
	consumable is in any of these states, the appropriate bit will
	be set. The cLowCondition will be set when the consumable
        reaches the engine low threshold, and cConfigurableLow will be
	set when the consumable reaches the Configurable Low threshold
	value. For non-cartridge supplies only cLowCondition,
	cOutCondition, and cMissing will be supported "
::= { consumables 7 }

-- 1.3.6.1.4.1.11.2.3.9.4.2.1.4.1.10.11. 
consumable-pages-printed-with-supply   OBJECT-TYPE
   SYNTAX          INTEGER    
   ACCESS           read-only    
   STATUS            optional   
   DESCRIPTION " This PML object returns the number of pages printed with a
   cartridge consumable. This PML object returns the value that
   should be displayed under 'Pages Printed With This Supply' for
   cartridges in color products"
::= { consumables 11 }

-- 1.3.6.1.4.1.11.2.3.9.4.2.1.1.4.8.2   
fih-extra-pulses-feature   OBJECT-TYPE
   SYNTAX          INTEGER {
                       eDisable(1),
                      eEnable(2)
               }   
   ACCESS           read-write    
   STATUS            optional   
   DESCRIPTION " This object allows one to get/set the setting of the FIH EXTRA
   PULSES FEATURE item. This either turns the feature on or off
   based on customer requirement"
::= { foreign-interface 2 }

-- 1.3.6.1.4.1.11.2.3.9.4.2.1.4.1.2.6   
total-mono-page-count   OBJECT-TYPE
   SYNTAX          INTEGER    
   ACCESS           read-only    
   STATUS            optional   
   DESCRIPTION " Total number of black pages printed by the device"
::= { status-prt-eng 6 }

-- 1.3.6.1.4.1.11.2.3.9.4.2.1.4.1.2.7   
total-color-page-count   OBJECT-TYPE
   SYNTAX          INTEGER    
   ACCESS           read-only    
   STATUS            optional   
   DESCRIPTION " Total number of color pages printed by the device"
::= { status-prt-eng 7 }

-- 1.3.6.1.4.1.11.2.3.9.4.2.1.4.1.2.22   
duplex-page-count   OBJECT-TYPE
   SYNTAX          INTEGER    
   ACCESS           read-only    
   STATUS            optional   
   DESCRIPTION " Total number of sheets of media that have been duplex printed.
   A sheet is counted if it travels through the duplex page path,
   regardless of whether or not marks are made on the page. The
   POS will indicate if the value is kept in NVRAM"
::= { status-prt-eng 22 }

-- 1.3.6.1.4.1.11.2.3.9.4.2.1.1.16.1.10   
source-tray-usage-total   OBJECT-TYPE
   SYNTAX          INTEGER    
   ACCESS           read-only    
   STATUS            optional   
   DESCRIPTION " This object reports the total source tray usage for the life of
   the printer. This value is reported on the usage page"
::= { printer-accounting 10 }

-- 1.3.6.1.4.1.11.2.3.9.4.2.1.1.16.1.11   
destination-bin-usage-total   OBJECT-TYPE
   SYNTAX          INTEGER    
   ACCESS           read-only    
   STATUS            optional   
   DESCRIPTION " This object reports the total destination bin usage for the
   life of the printer. This value is reported on the usage page"
::= { printer-accounting 11 }

-- 1.3.6.1.4.1.11.2.3.9.4.2.1.1.16.1.9   
printed-modes-usage-total   OBJECT-TYPE
   SYNTAX          INTEGER    
   ACCESS           read-only    
   STATUS            optional   
   DESCRIPTION "  This object reports the total color and mono print modes usage
   for the life of the printer. This value is reported on the
   usage page"
::= { printer-accounting 9 }

-- 1.3.6.1.4.1.11.2.3.9.4.2.1.1.16.1.12   
usage-printer-mono-total-charge   OBJECT-TYPE
   SYNTAX          INTEGER   
   ACCESS           read-only    
   STATUS            optional   
   DESCRIPTION " Total printer charge for all paper sizes printed in monochrome
   only "
::= { printer-accounting 12 }

-- 1.3.6.1.4.1.11.2.3.9.4.2.1.1.16.1.13   
usage-printer-color-total-charge   OBJECT-TYPE
   SYNTAX          INTEGER   
   ACCESS           read-only    
   STATUS            optional   
   DESCRIPTION " Total printer charge for all paper sizes printed in color
   only "
::= { printer-accounting 13 }

-- 1.3.6.1.4.1.11.2.3.9.4.2.1.1.16.1.2   
usage-printer-total-charge   OBJECT-TYPE
   SYNTAX           INTEGER  
   ACCESS           read-only    
   STATUS            optional   
   DESCRIPTION " Total printer charge for all paper sizes printed"
::= { printer-accounting 2 }

-- 1.3.6.1.4.1.11.2.3.9.4.2.1.1.16.1.15   
usage-printer-mono-simplex-total   OBJECT-TYPE
   SYNTAX          INTEGER    
   ACCESS           read-only    
   STATUS            optional   
   DESCRIPTION " This object reports the total of monochrome simplex pages
   printed on this device. This value is the sum of all
   PRINTED-MEDIA-SIMPLEX-COUNT.n counter values"
::= { printer-accounting 15 }

-- 1.3.6.1.4.1.11.2.3.9.4.2.1.1.16.1.16   
usage-printer-mono-duplex-total   OBJECT-TYPE
   SYNTAX          INTEGER    
   ACCESS           read-only    
   STATUS            optional   
   DESCRIPTION " This object reports the total of monochrome duplex pages
   printed on this device. This value is the sum of all
   PRINTED-MEDIA-DUPLEX-COUNT.n counter values"
::= { printer-accounting 16 }

-- 1.3.6.1.4.1.11.2.3.9.4.2.1.1.16.1.17   
usage-printer-mono-dimplex-total   OBJECT-TYPE
   SYNTAX          INTEGER    
   ACCESS           read-only    
   STATUS            optional   
   DESCRIPTION " This object reports the total of monochrome dimplex pages
   printed on this device. This value is the sum of all
   PRINTED-MEDIA-DIMPLEX-COUNT.n counter values"
::= { printer-accounting 17 }

-- 1.3.6.1.4.1.11.2.3.9.4.2.1.1.16.1.1.13   
printed-media-combined-simplex-total   OBJECT-TYPE
   SYNTAX          INTEGER    
   ACCESS           read-only    
   STATUS            optional   
   DESCRIPTION " Total number of simplex pages printed on this device"
::= { printed-media-usage 13 }

-- 1.3.6.1.4.1.11.2.3.9.4.2.1.1.16.1.1.14   
printed-media-combined-duplex-total   OBJECT-TYPE
   SYNTAX          INTEGER    
   ACCESS           read-only    
   STATUS            optional   
   DESCRIPTION " Total number of duplex pages printed on this device"
::= { printed-media-usage 14 }

-- 1.3.6.1.4.1.11.2.3.9.4.2.1.3.3.3.5   
pcl-total-page-count   OBJECT-TYPE
   SYNTAX          INTEGER    
   ACCESS           read-only    
   STATUS            optional   
   DESCRIPTION " Total number of PCL pages printed by the device"
::= { pdl-pcl 5 }

-- 1.3.6.1.4.1.11.2.3.9.4.2.1.3.3.4.5   
postscript-total-page-count   OBJECT-TYPE
   SYNTAX          INTEGER    
   ACCESS           read-only    
   STATUS            optional   
   DESCRIPTION " Total number of PostScript pages printed by the device"
::= { pdl-postscript 5 }

-- 1.3.6.1.4.1.11.2.3.9.4.2.1.3.3.15.2   
pdf-total-page-count   OBJECT-TYPE
   SYNTAX          INTEGER    
   ACCESS           read-only    
   STATUS            optional   
   DESCRIPTION " Total number of PDF pages printed by the device"
::= { pdl-pdf 2 }

-- 1.3.6.1.4.1.11.2.3.9.4.2.1.1.16.1.1.15   
impression-based-duplex-count-supported   OBJECT-TYPE
   SYNTAX          INTEGER {
                       eFalse(1),
                      eTrue(2)
               }   
   ACCESS           read-only    
   STATUS            optional   
   DESCRIPTION " The object is used to get the information on new duplex
   counting mechanism. With this new mechanism the Duplex count
   would represent actual Duplex count and not half of the count.
   eTrue means feature is available for the user"
::= { printed-media-usage 15 }

-- 1.3.6.1.4.1.11.2.3.9.4.2.1.1.16.5.1.1. 
source-tray-usage-count   OBJECT-TYPE
   SYNTAX          INTEGER    
   ACCESS           read-only    
   STATUS            optional   
   DESCRIPTION " Total number of pages printed from this source tray"
::= { source-tray-usage 1 }

-- 1.3.6.1.4.1.11.2.3.9.4.2.1.1.16.6.1.1. 
destination-bin-usage-count   OBJECT-TYPE
   SYNTAX          INTEGER    
   ACCESS           read-only    
   STATUS            optional   
   DESCRIPTION " Total number of pages printed to this destination bin"
::= { destination-bin-usage 1 }

-- 1.3.6.1.4.1.11.2.3.9.4.2.1.1.16.4.1.1. 
printed-modes-mono-count   OBJECT-TYPE
   SYNTAX          INTEGER    
   ACCESS           read-only    
   STATUS            optional   
   DESCRIPTION " Total number of mono pages printed in this fuser mode"
::= { printed-modes-usage 1 }

-- 1.3.6.1.4.1.11.2.3.9.4.2.1.1.16.4.1.3. 
printed-modes-color-count   OBJECT-TYPE
   SYNTAX          INTEGER    
   ACCESS           read-only    
   STATUS            optional   
   DESCRIPTION " Total number of color pages printed in this fuser mode"
::= { printed-modes-usage 3 }

-- 1.3.6.1.4.1.11.2.3.9.4.2.1.1.16.4.1.5. 
printed-modes-total-count   OBJECT-TYPE
   SYNTAX          INTEGER    
   ACCESS           read-only    
   STATUS            optional   
   DESCRIPTION " The total count for pages printed in this fuser mode"
::= { printed-modes-usage 5 }

-- 1.3.6.1.4.1.11.2.3.9.4.2.1.1.16.1.1.1. 
printed-media-simplex-count   OBJECT-TYPE
   SYNTAX          INTEGER    
   ACCESS           read-only    
   STATUS            optional   
   DESCRIPTION " Total number of simplex pages printed in this media size"
::= { printed-media-usage 1 }

-- 1.3.6.1.4.1.11.2.3.9.4.2.1.1.16.1.1.3. 
printed-media-duplex-count   OBJECT-TYPE
   SYNTAX          INTEGER    
   ACCESS           read-only    
   STATUS            optional   
   DESCRIPTION " Total number of duplex pages printed in this media size"
::= { printed-media-usage 3 }

-- 1.3.6.1.4.1.11.2.3.9.4.2.1.1.16.1.1.10. 
printed-media-dimplex-count   OBJECT-TYPE
   SYNTAX          INTEGER    
   ACCESS           read-only    
   STATUS            optional   
   DESCRIPTION " Total number of mono dimplex pages printed in this media size.
   A dimplex page is one that has been printed in duplex mode but
   the back side is blank. Dimplex pages occur when the printer
   firmware inserts a blank page in order to complete a duplexed
   job which is sent to the printer with an odd number of pages"
::= { printed-media-usage 10 }

-- 1.3.6.1.4.1.11.2.3.9.4.2.1.1.16.3.1.1. 
printed-media-color-simplex-count   OBJECT-TYPE
   SYNTAX          INTEGER    
   ACCESS           read-only    
   STATUS            optional   
   DESCRIPTION " Total number of color simplex pages printed in this media
   size"
::= { printed-media-color-usage 1 }

-- 1.3.6.1.4.1.11.2.3.9.4.2.1.1.16.3.1.3. 
printed-media-color-duplex-count   OBJECT-TYPE
   SYNTAX          INTEGER    
   ACCESS           read-only    
   STATUS            optional   
   DESCRIPTION " Total number of color duplex pages printed in this media size"
::= { printed-media-color-usage 3 }

-- 1.3.6.1.4.1.11.2.3.9.4.2.1.1.16.3.1.6. 
printed-media-color-dimplex-count   OBJECT-TYPE
   SYNTAX          INTEGER    
   ACCESS           read-only    
   STATUS            optional   
   DESCRIPTION " Total number of color dimplex pages printed in this media size.
   A color dimplex page is a color page that has been printed in
   duplex mode but the back side is blank. Dimplex pages occur
   when the printer firmware inserts a blank page in order to
   complete a duplexed job which is sent to the printer with an
   odd number of pages"
::= { printed-media-color-usage 6 }

-- 1.3.6.1.4.1.11.2.3.9.4.2.1.1.16.1.1.2. 
printed-media-simplex-charge   OBJECT-TYPE
   SYNTAX          INTEGER   
   ACCESS           read-write    
   STATUS            optional   
   DESCRIPTION " Charge for each simplex page printed in this media size"
::= { printed-media-usage 2 }

-- 1.3.6.1.4.1.11.2.3.9.4.2.1.1.16.1.1.4. 
printed-media-duplex-charge   OBJECT-TYPE
   SYNTAX          INTEGER   
   ACCESS           read-write    
   STATUS            optional   
   DESCRIPTION " Charge for each duplex page printed in this media size"
::= { printed-media-usage 4 }

-- 1.3.6.1.4.1.11.2.3.9.4.2.1.1.16.3.1.5. 
printed-media-color-total-count   OBJECT-TYPE
   SYNTAX          INTEGER   
   ACCESS           read-only    
   STATUS            optional   
   DESCRIPTION " The total count for color pages printed in this media size"
::= { printed-media-color-usage 5 }

-- 1.3.6.1.4.1.11.2.3.9.4.2.1.1.16.1.1.5. 
printed-media-total-charge   OBJECT-TYPE
   SYNTAX          INTEGER   
   ACCESS           read-only    
   STATUS            optional   
   DESCRIPTION " The total charge for pages printed in this media size"
::= { printed-media-usage 5 }

-- 1.3.6.1.4.1.11.2.3.9.4.2.1.1.16.1.1.7. 
printed-media-combined-total   OBJECT-TYPE
   SYNTAX          INTEGER   
   ACCESS           read-write    
   STATUS            optional   
   DESCRIPTION " Total number of letter equivalently weighted pages both color
   and mono combined with this printer"
::= { printed-media-usage 7 }

-- 1.3.6.1.4.1.11.2.3.9.4.2.1.1.16.1.1.11. 
printed-media-combined-simplex-count   OBJECT-TYPE
   SYNTAX          INTEGER    
   ACCESS           read-only    
   STATUS            optional   
   DESCRIPTION " Total number of simplex pages printed on this media size"
::= { printed-media-usage 11 }

-- 1.3.6.1.4.1.11.2.3.9.4.2.1.1.16.1.1.12. 
printed-media-combined-duplex-count   OBJECT-TYPE
   SYNTAX          INTEGER    
   ACCESS           read-only    
   STATUS            optional   
   DESCRIPTION " Total number of duplex pages printed on this media size"
::= { printed-media-usage 12 }

-- 1.3.6.1.4.1.11.2.3.9.4.2.1.1.16.1.14.4   
print-meter-simplex-count   OBJECT-TYPE
   SYNTAX          INTEGER    
   ACCESS           read-only    
   STATUS            optional   
   DESCRIPTION " Total number of simplex pages printed for this category of
   printed pages"
::= { print-meter-usage 4 }

-- 1.3.6.1.4.1.11.2.3.9.4.2.1.1.16.1.14.5   
print-meter-duplex-count   OBJECT-TYPE
   SYNTAX          INTEGER    
   ACCESS           read-only    
   STATUS            optional   
   DESCRIPTION " Total number of duplex pages printed for this category of
   printed pages"
::= { print-meter-usage 5 }

-- 1.3.6.1.4.1.11.2.3.9.4.2.1.1.16.1.14.7   
print-meter-dimplex-count   OBJECT-TYPE
   SYNTAX          INTEGER    
   ACCESS           read-only    
   STATUS            optional   
   DESCRIPTION " Total number of dimplex pages printed for this category of
   printed pages"
::= { print-meter-usage 7 }

-- 1.3.6.1.4.1.11.2.3.9.4.2.1.1.16.1.14.6   
print-meter-total-charge   OBJECT-TYPE
   SYNTAX          INTEGER   
   ACCESS           read-only    
   STATUS            optional   
   DESCRIPTION " Total number of simplex plus duplex pages printed multiplied by
   the unit charge for each given media size for this category of
   printed pages"
::= { print-meter-usage 6 }

-- 1.3.6.1.4.1.11.2.3.9.4.2.1.1.16.1.14.2. 
print-meter-usage-threshold   OBJECT-TYPE
   SYNTAX          INTEGER    
   ACCESS           read-only    
   STATUS            optional   
   DESCRIPTION " A value indicating the threshold value for this category of
   pages. The device POS will indicate the units of measure for
   this threshold value"
::= { print-meter-usage 2 }

-- 1.3.6.1.4.1.11.2.3.9.4.2.1.1.16.1.14.3. 
print-meter-print-quality   OBJECT-TYPE
   SYNTAX          INTEGER {
                       ePrintQualityMono(1),
                      ePrintQualityGood(2),
                      ePrintQualityBest(3)
               }   
   ACCESS           read-only    
   STATUS            optional   
   DESCRIPTION " This enumeration describes the selected print quality for this
   category of printed pages 
       "
::= { print-meter-usage 3 }

-- 1.3.6.1.4.1.11.2.3.9.4.2.1.1.16.1.14.8. 
print-meter-simplex-total   OBJECT-TYPE
   SYNTAX          INTEGER    
   ACCESS           read-only    
   STATUS            optional   
   DESCRIPTION " Total number of simplex pages printed for this category of
   printed pages"
::= { print-meter-usage 8 }

-- 1.3.6.1.4.1.11.2.3.9.4.2.1.1.16.1.14.9. 
print-meter-duplex-total   OBJECT-TYPE
   SYNTAX          INTEGER    
   ACCESS           read-only    
   STATUS            optional   
   DESCRIPTION " Total number of duplex pages printed for this category of
   printed pages"
::= { print-meter-usage 9 }

-- 1.3.6.1.4.1.11.2.3.9.4.2.1.1.16.1.14.10. 
print-meter-category-total   OBJECT-TYPE
   SYNTAX          INTEGER   
   ACCESS           read-only    
   STATUS            optional   
   DESCRIPTION " Total number of simplex plus duplex pages printed for this
   category of printed pages"
::= { print-meter-usage 10 }

-- 1.3.6.1.4.1.11.2.3.9.4.2.1.1.16.1.14.11. 
print-meter-dimplex-total   OBJECT-TYPE
   SYNTAX          INTEGER    
   ACCESS           read-only    
   STATUS            optional   
   DESCRIPTION " Total number of dimplex pages printed for this category of
   printed pages"
::= { print-meter-usage 11 }

-- 1.3.6.1.4.1.11.2.3.9.4.2.1.2.2.1.63   
scanner-accessory-total-copy-pages-printed   OBJECT-TYPE
   SYNTAX          INTEGER    
   ACCESS           read-only    
   STATUS            optional   
   DESCRIPTION " This relates to the number of copy pages printed on a device.
   The output sheet that is duplexed (made 2- sided) should be
   counted as 2 pages"
::= { settings-scanner 63 }

-- 1.3.6.1.4.1.11.2.3.9.4.2.1.1.16.1.44   
print-meter-equivalent-impression-count   OBJECT-TYPE
   SYNTAX           OCTET STRING   
   ACCESS           read-only    
   STATUS            optional   
   DESCRIPTION "This object reports the number of A4 equivalent impressions by
                color category and data source for all pages printed on this device.
		All printed impressions are normalized to a Letter/A4 sheet of
		media by dividing the area of the sheet by that of a Letter/A4
		sheet of media. This is a doubly indexed array object where the
		first OID binding is the impression category and the second OID
		binding is the data source for the printed impression. The
		possible categories are: \\ 
		    1 = Monochrome\\ 
		    2 = Color\\ 
		    3 = Composite Black\\ 
		    4 = General Office Accent\\ 
		    5 = General Office Color\\ 
		    6 = Professional Accent\\ 
		    7 = Professional Color\\ 
		    8 = Presentation Accent\\ 
		    9 = Presentation Color\\ 
		    10 = MAX DPI Accent\\ 
		    11 = MAX DPI Color\\ 
	            12 = Blank\\
		    13 = Total\\
		    14 = Accent Color\\
		    15 = Full Color\\ 
		    The possible media sizes are defined in the PCL
			Implementer’s Guide and in the Media Size Table near
			the end of this MIB.\\ 
		    The possible Data Sources are: \\ 
		    1 = Print (I/O Port or Internal Pages)\\ 
		    2 = Copy (Scanner)\\ 
		    3 = FAX (Modem)\\ 
		    The format for the OID is as follows: 1.1.16.1.44.m.p
			<---------> | | | | \ 
		    | | Data Source / \ 
		    / \ 
		Base OID Impression Category The device POS will indicate which
		impression categories and which data sources are
		supported/implemented for a given product.
		General office, Professional,Presentation & MaxDPI Impression categories
		are applicable only on OJMFPX585,OJX555 and future page wide array but not on LaserJet products.
		Refer to the FSMIBREADME.txt for instructions to convert to decimal equivalent.
		Impression count value has to be interpreted as  IEEE745 floating point single precision."
::= { printer-accounting 44 }


-- 1.3.6.1.4.1.11.2.3.9.4.2.1.1.16.1.20
print-meter-impression-count	OBJECT-TYPE
   SYNTAX     integer 
   ACCESS     read-only 
   STATUS      optional
   DESCRIPTION "This object reports the number of impressions by category and
		media size for printed pages received over the I/O ports for
		this device. This is a doubly indexed array object where the
		first OID binding is the impression category and the second OID
		binding is the media size. The possible impression categories
		are: \\ 
		    1 = Monochrome\\ 
		    2 = Color\\ 
		    3 = Composite Black\\ 
		    4 = General Office Accent\\ 
		    5 = General Office Color\\ 
		    6 = Professional Accent\\ 
		    7 = Professional Color\\ 
               8 = Presentation Accent\\ 
               9 = Presentation Color\\ 
               10 = Max DPI Accent\\ 
               11 = Max DPI Color\\
               12 = Blank\\
		    13 = Total\\
		    14 = Accent Color\\
		    15 = Full Color\\ 
		    The possible media sizes are defined in the PCL
			Implementer’s Guide and in the Media Size Table near
			the end of this MIB.\\ 
		    The format for the OID is as follows: 1.1.16.1.20.m.n
			<---------> | | | | \ 
		    | | Media Size / \ 
		    / \ 
		Base OID Impression Category The device POS will indicate which
		impression categories and which media sizes are
		supported/implemented on a given product.This object will be 
		enabled via feature authorization and will only be available
		to authorized customers." 
   INTERACTION "" 
   OPERATION  "Not destructive." 
-- STATUS     proposed 
   ::= { printer-accounting 20 } 



-- 1.3.6.1.4.1.11.2.3.9.4.2.1.1.16.1.26
print-meter-impression-copy-count OBJECT-TYPE
   SYNTAX     integer 
   ACCESS     read-only 
   STATUS      optional
   DESCRIPTION "This object reports the number of impressions by category and
		media size for printed pages received from the scanner on this
		device. This is a doubly indexed array object where the first
		OID binding is the impression category and the second OID
		binding is the media size. The possible categories are: \\ 
		    1 = Monochrome\\ 
		    2 = Color\\ 
		    3 = Composite Black\\ 
		    4 = General Office Accent\\ 
		    5 = General Office Color\\ 
		    6 = Professional Accent\\ 
		    7 = Professional Color\\
               8 = Presentation Color\\
               9 = Presentation Accent\\
               10 = Max DPI Accent\\
               11 = Max DPI Color\\
               12 = Blank\\
		    13 = Total\\
		    14 = Accent Color\\
		    15 = Full Color\\ 
		    The possible media sizes are defined in the PCL
			Implementer’s Guide and in the Media Size Table near
			the end of this MIB.\\ 
		    The format for the OID is as follows: 1.1.16.1.26.m.n
			<---------> | | | | \ 
		    | | Media Size / \ 
		    / \ 
		Base OID Impression Category The device POS will indicate which
		impression categories and which media sizes are
		supported/implemented on a given product.This object will be 
		enabled via feature authorization and will only be available 
		to authorized customers." 
   INTERACTION "" 
   OPERATION  "Not destructive." 
-- STATUS     proposed 
   ::= { printer-accounting 26 } 



-- 1.3.6.1.4.1.11.2.3.9.4.2.1.1.16.1.32
print-meter-impression-fax-count OBJECT-TYPE
   SYNTAX     integer 
   ACCESS     read-only 
   STATUS      optional
   DESCRIPTION "This object reports the number of impressions by category and
		media size for printed pages received from the FAX modem on
		this device. This is a doubly indexed array object where the
		first OID binding is the impression category and the second OID
		binding is the media size. The possible categories are: \\ 
		    1 = Monochrome\\ 
		    2 = Color\\ 
		    3 = Composite Black\\ 
		    4 = General Office Accent\\ 
		    5 = General Office Color\\ 
		    6 = Professional Accent\\ 
		    7 = Professional Color\\
		    8 = Presentation Accent\\
		    9 = Presentation Color\\
		    10 = Max DPI Accent\\
		    11 = Max DPI Color\\
		    12 = Blank\\
		    13 = Total\\
		    14 = Accent Color\\
		    15 = Full Color\\ 
		    The possible media sizes are defined in the PCL
			Implementer’s Guide and in the Media Size Table near
			the end of this MIB.\\ 
		    The format for the OID is as follows: 1.1.16.1.32.m.n
			<---------> | | | | \ 
		    | | Media Size / \ 
		    / \ 
		Base OID Impression Category The device POS will indicate which
		impression categories and which media sizes are
		supported/implemented for a given product.This object will be 
		enabled via feature authorization and will only be available
		to authorized customers." 
   INTERACTION "" 
   OPERATION  "Not destructive." 
-- STATUS     proposed 
   ::= { printer-accounting 32 } 



-- 1.3.6.1.4.1.11.2.3.9.4.2.1.1.16.1.38
print-meter-impression-count OBJECT-TYPE
   SYNTAX     integer 
   ACCESS     read-only 
   STATUS      optional
   DESCRIPTION "This object reports the number of impressions by category and
		media size for printed pages received on this device
		independent of the data source. This object reports the sum of
		Print, Copy and FAX impressions and is a doubly indexed array
		object where the first OID binding is the impression category
		and the second OID binding is the media size. The possible
		impression categories are: \\ 
		    1 = Monochrome\\ 
		    2 = Color\\ 
		    3 = Composite Black\\ 
		    4 = General Office Accent\\ 
		    5 = General Office Color\\ 
		    6 = Professional Accent\\ 
		    7 = Professional Color\\
		    8 = Presentation Accent\\
		    9 = Presentation Color\\
		    10 = Max DPI Accent\\
		    11 = Max DPI Color\\
		    12 = Blank\\
		    13 = Total\\
		    14 = Accent Color\\
		    15 = Full Color\\
		    The possible media sizes are defined in the PCL
			Implementer’s Guide and in the Media Size Table near
			the end of this MIB.\\ 
		    The format for the OID is as follows: 1.1.16.1.38.m.n
			<---------> | | | | \ 
		    | | Media Size / \ 
		    / \ 
		Base OID Impression Category The device POS will indicate which
		impression categories and which media sizes are
		supported/implemented for a given product.This object will be 
		enabled via feature authorization and will only be available
		to authorized customers." 
   INTERACTION "" 
   OPERATION  "Not destructive." 
-- STATUS     proposed  
   ::= { printer-accounting 38 } 





-- 1.3.6.1.4.1.11.2.3.9.4.2.1.1.16.1.47
print-meter-equivalent-impression-category-total OBJECT-TYPE
   SYNTAX     OCTET STRING
   ACCESS     read-only 
   STATUS      optional
   DESCRIPTION "This object reports the total equivalent number of impressions
		by category for all pages printed on this device. All printed
		impressions are normalized to a Letter/A4 sheet of media by
		dividing the area of the sheet by that of a Letter/A4 sheet of
		media. This is an array object where the OID binding is the
		page category for the printed impression. The possible
		categories are: \\ 
		    1 = Monochrome\\ 
		    2 = Color\\ 
		    3 = Composite Black\\ 
		    4 = General Office Accent\\ 
		    5 = General Office Color\\ 
		    6 = Professional Accent\\ 
		    7 = Professional Color\\
		    8 = Presentation Accent\\
		    9 = Presentation Color\\
		    10 = Max DPI Accent\\
		    11 = Max DPI Color\\
		    12 = Blank\\
		    13 = Total\\
		    14 = Accent Color\\
		    15 = Full Color\\ 
		    The format for the OID is as follows: 1.1.16.1.47.m
			<---------> | | | | | / \ 
		    / \ 
		Base OID Impression Category The device POS will indicate which
		categories are supported/implemented for a given product.This object will be 
		enabled via feature authorization and will only be available
		to authorized customers." 
   INTERACTION "" 
   OPERATION  "Not destructive." 
-- STATUS     proposed 
   ::= { printer-accounting 47 } 
   

-- 1.3.6.1.4.1.11.2.3.9.4.2.1.1.16.1.59   
print-meter-equivalent-impression-coverage OBJECT-TYPE
   SYNTAX     OCTET STRING  
   ACCESS     read-only 
   STATUS      optional
   DESCRIPTION "This object reports the number of A4 equivalent impressions by
		marker color and by the percentage coverage for each color
		compared to the ISO Yield Page - for printed pages received
		over the I/O ports for this device. This is a doubly indexed
		array object where the first OID binding is the marker color
		and the second OID binding is the impression coverage area
		compared to the ISO Yield page. The possible marker colors are
		typically: 1 = Black 2 = Cyan 3 = Magenta 4 = Yellow The actual
		mapping for this OID binding can be discovered by walking the
		prtMarkerSuppliesDescription objects. The possible coverage
		categories along with their enumerations and descriptions are
		listed in 'Contractual Coverage Table' near the end of this
		document. The format for the OID is as follows: 1.1.16.1.59.m.n
		m represents the marker color n represents the coverage
		category Each of these SNMP objects/counters has a
		corresponding DUSI(Web Service) counter from Device-printer-
		A4EquivalentImpressionsByMarkerColor counter group.This object will be 
		enabled via feature authorization and will only be available
		to authorized customers." 
   INTERACTION "" 
   OPERATION  "Not destructive." 
-- STATUS     proposed 
   ::= { printer-accounting 59 } 


-- 1.3.6.1.4.1.11.2.3.9.4.2.1.1.16.1.60
print-meter-equivalent-impression-coverage-bytime OBJECT-TYPE
   SYNTAX     OCTET STRING
   ACCESS     read-only 
   STATUS      optional
   DESCRIPTION "This object reports the number of A4 equivalent impressions by
		marker color and by the percentage coverage for each color
		compared to the ISO Yield Page - for printed pages received
		over the I/O ports for this device. This is a three dimensional
		array object where the first OID binding is the time period,
		the second OID binding is the marker color and the third OID
		binding is the impression coverage area compared to the ISO
		Yield page. The possible time period ID integer values consist
		of values greater than 0. The first time period
		(1.1.16.1.60.1.n.o) is always the current time period. The
		possible marker colors are typically: 1 = Black 2 = Cyan 3 =
		Magenta 4 = Yellow The actual mapping for this OID binding can
		be discovered by walking the prtMarkerSuppliesDescription
		objects. The possible coverage categories along with their
		enumerations and descriptions are listed in 'Contractual
		Coverage Table' near the end of this document. The format for
		the OID is as follows: 1.1.16.1.60.m.n.o m represents the time
		period n represents the marker color o represents the coverage
		category Each of these SNMP objects/counters has a
		corresponding DUSI(Web Service) counter from
		Device-printer-A4EquivalentImpressionsByTimePeriod-
		A4EquivalentImpressionsByMarkerColor counter group.This object will be 
		enabled via feature authorization and will only be available
		to authorized customers" 
   INTERACTION "" 
   OPERATION  "Not destructive." 
-- STATUS     proposed 
   ::= { printer-accounting 60 }


-- 1.3.6.1.4.1.11.2.3.9.4.2.1.1.16.1.61
 print-meter-equivalent-impression-coverage-bytime-interval OBJECT-TYPE
   SYNTAX     integer
   ACCESS     read-only 
   STATUS      optional
   DESCRIPTION "This object reports the number of days in each contractual
		coverage time period. For example if the number of days in each
		contractual coverage time period is 30 days - then this object
		will return a value of 30.This object will be 
		enabled via feature authorization and will only be available
		to authorized customers" 
   INTERACTION "" 
   OPERATION  "Not destructive." 
-- STATUS     proposed 
   ::= { printer-accounting 61 }  



-- 1.3.6.1.4.1.11.2.3.9.4.2.1.1.2.59
host-application-available-memory   OBJECT-TYPE
   SYNTAX          INTEGER    
   ACCESS           read-only    
   STATUS            optional   
   DESCRIPTION "Returns the amount of memory, in bytes, that the device has
   available for job-related processing or resources. Also known
   as driver work space (DWS) memory.
       "
::= { status-system 59 }
-- 1.3.6.1.4.1.11.2.3.9.4.2.1.3.3.15.1   
pdf-version   OBJECT-TYPE
   SYNTAX          OCTET STRING    
   ACCESS           read-only    
   STATUS            optional   
   DESCRIPTION " Contains version of PDF that is supported on the device"
::= { pdl-pdf 1 }

-- 1.3.6.1.4.1.11.2.3.9.4.2.1.3.3.15.3   
pdf-enabled   OBJECT-TYPE
   SYNTAX          INTEGER {
                       ePDFNotEnabled(1),
                      ePDFEnabled(2)
               }   
   ACCESS           read-only    
   STATUS            optional   
   DESCRIPTION " Used to tell whether the device supports PDF"
::= { pdl-pdf 3 }

-- 1.3.6.1.4.1.11.2.3.9.4.2.1.3.3.4.11   
postscript-print-errors   OBJECT-TYPE
   SYNTAX          INTEGER {
                       eOff(1),
                      eOn(2)
               }   
   ACCESS           read-write    
   STATUS            optional   
   DESCRIPTION " Returns or changes the value of the print PostScript errors
   setting. If eOn, PostScript prints an error page showing the
   error encountered and the stack at the time of the error"
::= { pdl-postscript 11 }

-- 1.3.6.1.4.1.11.2.3.9.4.2.1.3.3.15.4   
pdf-print-errors   OBJECT-TYPE
   SYNTAX          INTEGER {
                       eOff(1),
                      eOn(2)
               }   
   ACCESS           read-write    
   STATUS            optional   
   DESCRIPTION " Returns or changes the value of the print PDF errors setting.
   If eOn, PDF prints an error page showing the error encountered
   and the stack at the time of the error"
::= { pdl-pdf 4 }

-- 1.3.6.1.4.1.11.2.3.9.4.2.1.4.1.6.7   
default-print-quality   OBJECT-TYPE
   SYNTAX          INTEGER (0..100)    
   ACCESS           read-write    
   STATUS            optional   
   DESCRIPTION " Returns or sets the default print quality. A value of zero has
   the lowest print quality. A value of 100 has the highest print
   quality. Each POS should document what values in the 0 to 100
   range are supported"
::= { imaging 7 }



-- 1.3.6.1.4.1.11.2.3.9.4.2.1.3.3.4.14   
postscript-defer-media   OBJECT-TYPE
   SYNTAX          INTEGER {
                       eDisabled(1),
                      eEnabled(2)
               }   
   ACCESS           read-write    
   STATUS            optional   
   DESCRIPTION " This object will be used to enable or disable the use of the
   Adobe Postscript Paper Handling Model in the printer firmware.
   By default it is enabled which means that PostScript will
   always defer the media selection to HP Paper Handling Model"
::= { pdl-postscript 14 }

-- 1.3.6.1.4.1.11.2.3.9.4.2.1.3.3.1.11   
default-lines-per-page   OBJECT-TYPE
   SYNTAX          INTEGER    
   ACCESS           read-write    
   STATUS            optional   
   DESCRIPTION " Returns or changes the default number of lines per page. The
   POS indicates the supported values. An unsupported value causes
   the printer to use the closest supported value, causing the
   printer to return the <OKNearestLegalValueSubstituted>"
::= { settings-pdl 11 }

-- 1.3.6.1.4.1.11.2.3.9.4.2.1.3.3.1.39   
default-bits-per-pixel   OBJECT-TYPE
   SYNTAX          INTEGER    
   ACCESS           read-write    
   STATUS            optional   
   DESCRIPTION " Controls the number of levels used (per pixel) when printing
   grayscale or color images"
::= { settings-pdl 39 }

-- 1.3.6.1.4.1.11.2.3.9.4.2.1.3.3.1.12   
default-vmi   OBJECT-TYPE
   SYNTAX          INTEGER    
   ACCESS           read-write    
   STATUS            optional   
   DESCRIPTION " Returns or changes the default vertical motion index. The unit
   of measure for VMI is centipoints per line. The POS indicates
   the supported values. An unsupported value causes the printer
   to use the closest supported value, causing the printer to
   return <OKNearestLegalValueSubstituted>"
::= { settings-pdl 12 }

-- 1.3.6.1.4.1.11.2.3.9.4.2.1.3.3.3.14   
pcl-default-font-source   OBJECT-TYPE
   SYNTAX          INTEGER {
                       eInternal(1),
                      ePermanentSoft(2),
                      eRomSimm1(10),
                      eRomSimm2(11),
                      eRomSimm3(12),
                      eRomSimm4(13),
                      eRomSimm5(14),
                      eUsb1(15),
                      eUsb2(16),
                      eUsb3(17),
                      eUsb4(18)
               }   
   ACCESS           read-write    
   STATUS            optional   
   DESCRIPTION " Returns or changes the value of the default font source
   variable in NVRAM  "
::= { pdl-pcl 14 }

-- 1.3.6.1.4.1.11.2.3.9.4.2.1.3.3.3.15   
pcl-default-font-number   OBJECT-TYPE
   SYNTAX          INTEGER    
   ACCESS           read-write    
   STATUS            optional   
   DESCRIPTION " Returns or changes the value of the default font number
   variable in NVRAM. Writing an unsupported value causes the
   printer to generate an <ErrorInvalidOrUnsupportedValue> 
   , eclipse    "
::= { pdl-pcl 15 }

-- 1.3.6.1.4.1.11.2.3.9.4.2.1.3.3.1.9   
default-horizontal-black-resolution   OBJECT-TYPE
   SYNTAX          INTEGER    
   ACCESS           read-write    
   STATUS            optional   
   DESCRIPTION " Returns or changes the value of the default horizontal black
   resolution. The units are dots per inch"
::= { settings-pdl 9 }

-- 1.3.6.1.4.1.11.2.3.9.4.2.1.3.3.1.8   
default-vertical-black-resolution   OBJECT-TYPE
   SYNTAX          INTEGER    
   ACCESS           read-write    
   STATUS            optional   
   DESCRIPTION " Returns or changes the value of the default vertical black
   resolution. The units are dots per inch"
::= { settings-pdl 8 }

-- 1.3.6.1.4.1.11.2.3.9.4.2.1.4.1.6.5   
default-ret   OBJECT-TYPE
   SYNTAX          INTEGER {
                       eOff(1),
                      eLight(2),
                      eMedium(3),
                      eDark(4),
                      eNotSet(5)
               }   
   ACCESS           read-write    
   STATUS            optional   
   DESCRIPTION " Returns or changes the Resolution Enhancement Technology
   setting. Devices that only support eOff and eOn should map all
   other values to eOn and always return the same non-eOff value
   to indicate on. The list of supported values should be
   documented in the device POS"
::= { imaging 5 }

-- 1.3.6.1.4.1.11.2.3.9.4.2.1.3.3.1.4   
default-copies   OBJECT-TYPE
   SYNTAX          INTEGER    
   ACCESS           read-write    
   STATUS            optional   
   DESCRIPTION " Returns or changes default copies. Default copies is the
   default values used by the PDL to control the number of copies
   of each page in the print job that are printed. The print job
   can override this value. The list of supported values should be
   documented in the device POS"
::= { settings-pdl 4 }

-- 1.3.6.1.4.1.11.2.3.9.4.2.1.3.3.1.5   
form-feed   OBJECT-TYPE
   SYNTAX          INTEGER {
                       eInitiateAction(1)
               }   
   ACCESS           write-only    
   STATUS            optional   
   DESCRIPTION " Instructs the PDL processing sub-system to finishing processing
   the current page of the current job. Form feed is also known as
   close page or eject page. If the PDL processing sub-system is
   in a FORM-FEED-NEEDED state, this causes the device to flush or
   finish processing the current page of the current job. If the
   device is not in the FORM-FEED-NEEDED state, an
   <ErrorActionCanNotBePerformedNow> will occur"
::= { settings-pdl 5 }

-- 1.3.6.1.4.1.11.2.3.9.4.2.1.3.3.2.2   
form-feed-needed   OBJECT-TYPE
   SYNTAX          INTEGER {
                       eFalse(1),
                      eTrue(2)
               }   
   ACCESS           read-only    
   STATUS            optional   
   DESCRIPTION " Indicates if the PDL processing sub-system has made marks on
   the current page and the source subsystem has been idle for a
   device specific amount of time"
::= { status-pdl 2 }

-- 1.3.6.1.4.1.11.2.3.9.4.2.1.3.5.4   
pjl-device-access   OBJECT-TYPE
   SYNTAX           INTEGER {
                       eDisabled(1),
                      eEnabled(2)
               }   
   ACCESS            read-write    
   STATUS            optional   
   DESCRIPTION " This object is used to enable or disable PJL device attendance
   commands,SNMP passthrough commands and environment commands
   which affect persistent settings on the device.These include
   OPMSG,RDYMSG,STMSG,DMINFO,DMCMD, DEFAULT,INITIALISE and SET on
   default same-as-current PJL variables.By default this object is  enabled"
::= { pjl 4 }

-- 1.3.6.1.4.1.11.2.3.9.4.2.1.4.1.1.3   
override-media-size   OBJECT-TYPE
   SYNTAX          INTEGER {
                       eUSExecutive(1),
                      eUSLetter(2),
                      eUSLegal(3),
                      eUSEDP(4),
                      eEuropeanEDP(5),
                      eReservedDoNotUse(6),
                      eUSGovernmentLetter(7),
                      eUSGovernmentLegal(8),
                      eFolio(9),
                      eFoolscap(10),
                      eLedger(11),
                      eCSize(12),
                      eDSize(13),
                      eESize(14),
                      eStatement(15),
                      eSuperB(16),
                      eROC16K(17),
                      eJISExecutive(18),
                      eROC8K(19),
                      eISOandJISA10(20),
                      eISOandJISA9(21),
                      eISOandJISA8(22),
                      eISOandJISA7(23),
                      eISOandJISA6(24),
                      eISOandJISA5(25),
                      eISOandJISA4(26),                            
                      eISOandJISA3(27),                      
                      eISOandJISA2(28),
                      eISOandJISA1(29),
                      eISOandJISA0(30),
                      eISOandJIS2A0(31),
                      eISOandJIS4A0(32),
                      ePRC8K270X390(33),
                      ePRC16K195X270(34),
                      ePRC8K260X368(35),
                      eJISB10(40),
                      eJISB9(41),
                      eJISB8(42),
                      eJISB7(43),
                      eJISB6(44),
                      eJISB5(45),
                      eJISB4(46),
                      eJISB3(47),
                      eJISB2(48),
                      eJISB1(49),
                      eJISB0(50),
                      eISOB10(60),
                      eISOB9(61),
                      eISOB8(62),
                      eISOB7(63),
                      eISOB6(64),
                      eISOB5(65),
                      eISOB4(66),
                      eISOB3(67),
                      eISOB2(68),
                      eISOB1(69),  
                      eISOB0(70),
                      eJapansePostcardSingle(71),
                      eJapansePostcardDouble(72),
                      eISOA6Postcard(73),
                      eIndexCard4x6(74),
                      eIndexCard5x8(75),
                      ePhoto4x6(76),
                      eJapanesePostcardWithTab(77),
                      eIndexCard3x5(78),
                      eMonarch(80),
                      eCommercial10(81),
                      eCatalog(82),
                      eNo10Envelope(83),
                      ePRC16K184X260(89),
                      eInternationalDL(90),
                      eInternationalC5(91),
                      eInternationalC6(92),
                      eInternationalC4(93),
                      eInternationalB5(100),
                      eCustom(101),
                      eEnvelope9(102),
                      eCustomCard(108),
                      eUSEnvelopeA2(109),
                      eJapanseEnvLong3(110),
                      eJapanseEnvLong4(111),
                      eJapaneseEnv2(112),
                      ePhoto10x15(118), 
                      ePhotoCabinet(119),
                      ePhotoLSizeCard(121),
                      eIndexCard5x7(122),
                      ePhotoESizeCard(123),
                      ePhotoKGSizeCard(124),
                      ePhoto2ESizeCard(125),
                      ePhoto2LSizeCard(126),
                      eUSExecutiveR(257),
                      eUSLetterR(258),
                      eROC16KR(273),
                      eISOandJISA6R(280),
                      eISOandJISA5R(281),
                      eISOandJISA4R(282),
                      eJISBR6R(300),
                      eJISB5R(301),
                      eStatementR(302),
                      eAnyCustomSize(32764),
                      eAnySize(32765),
                      eCustomRoll(32766),
                      eUnknownMediaSize(32767),
                      eStatementWR(65234),
                      eJISB5WR(65235),
                      eISOandJISA4WR(65254),
                      eISOandJISA5WR(65255),
                      eUSLetterWR(65278),
                      eJISB4W(65490),
                      eJISB5W(65491),
                      eISOandJISA3W(65509),
                      eISOandJISA4W(65510),
                      eISOandJISA5W(65511),
                      eStatementW(65521),
                      eLedgerW(65530),
                      eUSLetterW(65534)
               }   
   ACCESS           read-write    
   STATUS            optional   
   DESCRIPTION " Sets the media size that is to be used in place of the
   currently requested media size"
::= { settings-prt-eng 3 }

-- 1.3.6.1.4.1.11.2.3.9.4.2.1.4.1.1.2   
override-media-name   OBJECT-TYPE
   SYNTAX          OCTET STRING    
   ACCESS           read-write    
   STATUS            optional   
   DESCRIPTION " Sets a string identifying the media name that is to be used in
   place of the currently requested media. The substitution will
   continue until another media is selected. If set to a named
   media that is not currently available the requested media is
   not overridden"
::= { settings-prt-eng 2 }

-- 1.3.6.1.4.1.11.2.3.9.4.2.1.4.1.8.4.1   
engine-media-modes-supported1   OBJECT-TYPE
   SYNTAX          OCTET STRING    
   ACCESS           read-only    
   STATUS            optional   
   DESCRIPTION " The list of engine media modes supported by the device. The
   modes are each separated by a comma character. An example
   string would be: 'Normal,Rough,Low,Vellum'"
::= { media-modes 1 }

-- 1.3.6.1.4.1.11.2.3.9.4.2.1.4.1.1.31   
finisher-image-rotation   OBJECT-TYPE
   SYNTAX          OCTET STRING    
   ACCESS           read-write    
   STATUS            optional   
   DESCRIPTION " This PML object will provide the additional image rotation that
   is applied to a printed job depending on the presence or
   absence of a finisher device or the value of the
   SVM_ALWAYS_MATCH_OUTPUT_ORIENTATION variable"
::= { settings-prt-eng 31 }

-- 1.3.6.1.4.1.11.2.3.9.4.2.1.1.6.2.1.1   
current-job-parsing-id   OBJECT-TYPE
   SYNTAX          INTEGER    
   ACCESS           read-only    
   STATUS            optional   
   DESCRIPTION " Contains the printer assigned job identification for the job
   currently being processed by the processing PDL sub-system. The
   job ID is a monotonically increasing number. The job ID may be
   reset to zero at power-up and may roll over to zero after
   reaching some maximum value"
::= { job-being-parsed 1 }

-- 1.3.6.1.4.1.11.2.3.9.4.2.1.1.6.5.10. 
job-info-stage   OBJECT-TYPE
   SYNTAX          INTEGER {
                       cSourceSubsystem(0),
                      cProcessingSubsystem(1),
                      cDestinationSubsystem(2)
               }   
   ACCESS           read-only    
   STATUS            optional   
   DESCRIPTION " Indicates what printer sub-systems are currently processing
   this print job. The last OID field for this dynamic object
   contains the job ID. cSourceSubsystem - some of the job is in
   the printer I/O subsystem. cProcessingSubsystem - some of the
   job is in the printer imaging processing subsystem.
   cDestinationSubsystem - some of the job is being printed"
::= { job-info 10 }

-- 1.3.6.1.4.1.11.2.3.9.4.2.1.1.6.5.24. 
job-info-requested-originals   OBJECT-TYPE
   SYNTAX          INTEGER    
   ACCESS           read-only    
   STATUS            optional   
   DESCRIPTION " The number of requested collated copies. The value was supplied
   with the job via PJL QTY variable, the PostScript Collate and
   NumCopies entries in the page device dictionary, or via some
   other mechansim"
::= { job-info 24 }

-- 1.3.6.1.4.1.11.2.3.9.4.2.1.1.6.5.25. 
job-info-page-count-current-original   OBJECT-TYPE
   SYNTAX          INTEGER    
   ACCESS           read-only    
   STATUS            optional   
   DESCRIPTION " The page number being printed within the current copy of a
   collated multi-copy job. This value changes when the
   job-info-pages-printed changes. The job-info-pages-printed
   indicates the total number of pages printed in the job, while
   this object indicates the number of pages printed for this copy
   of a collated multi-copy job"
::= { job-info 25 }

-- 1.3.6.1.4.1.11.2.3.9.4.2.1.1.6.5.26. 
job-info-pages-in-original   OBJECT-TYPE
   SYNTAX          INTEGER    
   ACCESS           read-only    
   STATUS            optional   
   DESCRIPTION " Number of pages in a single copy of a collated multi-copy job 
      "
::= { job-info 26 }

-- 1.3.6.1.4.1.11.2.3.9.4.2.1.1.6.5.27. 
job-info-printed-originals   OBJECT-TYPE
   SYNTAX          INTEGER    
   ACCESS           read-only    
   STATUS            optional   
   DESCRIPTION " Number of collated copies completely printed and delivered to
   the output bin at time of query"
::= { job-info 27 }

-- 1.3.6.1.4.1.11.2.3.9.4.2.1.1.5.2   
print-internal-page   OBJECT-TYPE
   SYNTAX          INTEGER {
                       eNotPrintingAnInternalPage(1),
                      ePrintingAnUnknownInternalPage(2),
                      eDeviceDemoPage1ConfigurationPage(3),
                      eDeviceDemoPage2(4),
                      eDeviceDemoPage3SpeedDialPage(5),
                      eDeviceDemoPage4ExtensiveDeviceInformation(6)
,                     eDeviceDemoPage5ErrorLog(7),
                      eDeviceDemoPage6FileSystemDirectoryListing(8),
                      eDeviceDemoPage7MenuMap(9),
                      eDeviceUsagePage(10),
                      eDeviceDemoPage8BlockFaxList(11),
                      eDeviceDemoPage9FaxLogReport(12),
                      eServicePage(13),
                      eServicePageWarningLog(14),
                      eServicePageJamHistory(15),
                      eServicePageServiceSummary(16),
                      eServicePageServiceSettings(17),
                      eServicePagePM(18),
                      ePrintUsagePage(100),            
                      eSuppliesPage(101),
                      eMediaPathUsagePage(102),
                      eSuppliesUsagePage(103),
                      eDeviceADFAdjustmentPages(250),
                      eDeviceColorRegistrationPage(251),
                      eDeviceAutoCleaningPage(252),
                      eDeviceCleaningPage(253),
                      eDevicePaperPathTest(254),
                      eDevicePageRegistrationPage(255),
                      ePrintQualityPages(256),
                      eHighVoltageTestPage(257),
                      eColorPaletteRGBPage(258),
                      eColorPaletteCMYKPage(259),
                      eDevicePageDiagnosticsPage(260),
                      eDevicePageStoredJobsPage(261),
                      eSWActivatedRibSmearCleanerPage(262),
                      eSWActivatedPickTireCleanerPage(263),
                      eXPSErrorPage(264),
                      ePCLDemoPage1ConfigurationPage(300),
                      ePCLDemoPage2(301),                      
                      ePCLFontList1(350),                     
                      ePCLFontList2(352),
                      ePCLXLFontList(353),
                      ePostScriptDemoPage1ConfigurationPage(400),
                      ePostScriptDemoPage2(401),
                      ePostScriptFontList1(450),
                      ePostScriptFontList2(451),
                      eEscPDemoPage1ConfigurationPage(500),
                      eEscPDemoPage2(501),
                      eEscPFontList1(550),
                      eEscPFontList2(551),
                      eEpsonDemoPage1ConfigurationPage(600),
                      eEpsonDemoPage2(601),
                      eEpsonFontList1(650),
                      eEpsonFontList2(651),
                      eIPDSDemoPage1ConfigurationPage(700),
                      eIPDSDemoPage2(701),
                      eIPDSFontList1(750),
                      eIPDSFontList2(751),
                      eHPGLDemoPage1ConfigurationPage(800),
                      eHPGLDemoPage2(801),
                      eHPGLFontList1(850),                      
                      eHPGLFontList2(851),                      
                      eHPGL2DemoPage1ConfigurationPage(900),
                      eHPGL2DemoPage2(901),
                      eHPGL2FontList1(950),
                      eHPGL2FontList2(951),
                      eMarkingAgentTestPattern(1000),
                      eCalibrationNormalPage(1100),
                      eCalibrationPhotoPage(1101),
                      eColorCalibrationPage(1102),
                      eColorCalConfirmPage(1103),
                      ePenAlignmentPage(1150),
                      ePenAlignmentVerificationPage(1151),
                      ePrintSimplifiedAlignmentPage(1152),
                      eNetworkConfigPage(1200),
                      eNetworkConfigMultiLangPage(1201),
                      eWirelessNetworkTestPage(1202),
                      eFaxSelfTestShort(1300),
                      eFaxSelfTestPage(1301),
                      eFaxSelfTestExtended(1302),
                      ePDFEaterErrorPage(1303),
                      eFaxActivityLogPage(1304),            
                      eFaxCallReportPage(1305),
                      eFaxCallReportOnEventPage(1306),
                      eBillingReportPage(1307),
                      eSpeedDialListReportPage(1308),
                      eBlockedFaxListReportPage(1309),
                      eT30TracerReportPage(1310),
                      eT30TracerReportOnEventPage(1311),
                      eDeviceShowMeHowPageClearJams(1400),
                      eDeviceShowMeHowPageLoadTrays(1401),
                      eDeviceShowMeHowPageLoadSpecialMedia(1402),
                      eDeviceShowMeHowPagePrintBothSides(1403),
                      eDeviceShowMeHowPageSupportedPaper(1404),
                      eDeviceShowMeHowPageMoreHelp(1405),
                      eDeviceShowMeHowHelpGuide(1406),
                      eAutomaticLinefeedCalibration(1407),
                      eAutomaticColorCalibration(1408),
                      ePrintQualityDiagnosticPage(1409),
                      eCurrentSettingsPage(1410),                      
                      eDeviceShowMeHowPageLoadMedia4x6(1411),
                      eColorUsageLog(1412)
               }   
   ACCESS           read-write   
   STATUS            optional   
   DESCRIPTION " Writing this object to a value other than
   eNotPrintingAnInternalPage causes the device to attempt to
   print an internally generated page. Reading this object
   provides an indication what internally generated page is
   currently being printed, if any. The actual page is device
   specific. Some devices may support continuously printing an
   internally generated page. Setting this object to
   eNotPrintingAnInternalPage terminates continuously printing
   internally generated pages. An internally generated page may
   not be allowed to be printed at any arbitrary time; under what
   conditions it will succeed or fail is device specific. If the
   device supports the requested page, but can not start printing
   the page when requested, the device will respond with
   <ErrorActionCanNotBePerformedNow>. RECOMMENDATION: If the
   device is ready (i.e. the NOT-READY-PRINTER object does not
   contain any items, except maybe being off-line) and is idle
   (i.e. the NOT-IDLE object does not contain any items), 
   this
   request should always succeed. This provides a mechanism for
   driver writers to always determine if the action will succeed
   or not"
::= { test 2 }

-- 1.3.6.1.4.1.11.2.3.9.4.2.1.2.2.2.15
instant-lamp-mode   OBJECT-TYPE
   SYNTAX          INTEGER {                       
                                      eDisabled(1),                      
				      eEnabled(2)               }   
   ACCESS           read-write    
   STATUS            optional   
   DESCRIPTION "Indicates whether the 'Instant Lamp On' mode in enabled or not.
   It returns eDisabled if 'Instant Lamp On' mode is disabled, and
   eEnabled if 'Instant Lamp On' mode is enabled. The 'Instant
   Lamp On' mode allows faster scanning by reducing lamp warm up
   time at the expense of greater energy consumption.
       "
::= { status-scanner 15 }

-- 1.3.6.1.4.1.11.2.3.9.4.2.1.2.2.1.102
adf-description   OBJECT-TYPE
   SYNTAX          OCTET STRING    
   ACCESS           read-only    
   STATUS            optional   
   DESCRIPTION"Returns the product 
   DESCRIPTION of the scanner automatic	document feeder accessory.
       "
::= { settings-scanner 102 }

-- 1.3.6.1.4.1.11.2.3.9.4.2.1.2.2.1.109
adf-maintenance-count   OBJECT-TYPE
   SYNTAX          INTEGER    
   ACCESS           read-write    
   STATUS            optional   
   DESCRIPTION "The total number of times maintenance has been performed on an
   automatic document feeder.
       "
::= { settings-scanner 109 }

-- 1.3.6.1.4.1.11.2.3.9.4.2.1.2.2.1.108
adf-maintenance-current-state   OBJECT-TYPE
   SYNTAX          INTEGER{                       cMaintenanceRecommended(0)               }   
   ACCESS           read-only    
   STATUS            optional   
   DESCRIPTION "This PML object returns the current state of the ADF regarding
   recommended maintenance. For example, some products require
   that the paper path be cleaned with a cleaning cloth on a
   periodic basis. The bits are: cMaintenanceRecommended -
   maintenance of the ADF is recommended when this bit is set.
       "
::= { settings-scanner 108 }

-- 1.3.6.1.4.1.11.2.3.9.4.2.1.2.2.1.103
adf-maximum-capacity   OBJECT-TYPE
   SYNTAX          INTEGER    
   ACCESS           read-only    
   STATUS            optional   
   DESCRIPTION "Returns the maximum capacity of the Scanner automatic document
   feeder as specified in ADF-MEASUREMENT-UNITS. If the
   ADF-MEASUREMENT-UNITS OID is not implemented, then assume it is
   sheets of 20 pound paper.
       "
::= { settings-scanner 103 }

-- 1.3.6.1.4.1.11.2.3.9.4.2.1.2.2.1.104
adf-measurement-units   OBJECT-TYPE
   SYNTAX          INTEGER {                       eOther(2),                      ePages(5)               }   
   ACCESS           read-only    
   STATUS            optional   
   DESCRIPTION "This object is used to report the units used to measure the
   maximum capacity of an automatic document feeder.
      "
::= { settings-scanner 104 }

-- 1.3.6.1.4.1.11.2.3.9.4.2.1.2.2.1.101
adf-model-number   OBJECT-TYPE
   SYNTAX          OCTET STRING    
   ACCESS           read-only    
   STATUS            optional   
   DESCRIPTION "Returns the model number of the scanner automatic document
   feeder accessory.
   d    "
::= { settings-scanner 101 }

-- 1.3.6.1.4.1.11.2.3.9.4.2.1.2.2.1.110
adf-pages-since-maintenance   OBJECT-TYPE
   SYNTAX          INTEGER    
   ACCESS           read-write    
   STATUS            optional   
   DESCRIPTION "The total number of pages fed since the last maintenance was
   performed on the automatic document feeder.
       "
::= { settings-scanner 110 }

-- 1.3.6.1.4.1.11.2.3.9.4.2.1.4.1.10.18
consumable-pages-since-replacement   OBJECT-TYPE
   SYNTAX          INTEGER    
   ACCESS           read-write    
   STATUS            optional   
   DESCRIPTION "The total number of pages fed since the last replacement of the
   consumable.
       "
::= { consumables 18 }

-- 1.3.6.1.4.1.11.2.3.9.4.2.1.4.1.10.16
consumable-replacement-count   OBJECT-TYPE
   SYNTAX          INTEGER    
   ACCESS           read-write    
   STATUS            optional   
   DESCRIPTION "The total number of times a consumable has been replaced.
       "
::= { consumables 16 }

-- 1.3.6.1.4.1.11.2.3.9.4.2.1.1.16.2.1.5
scanned-media-total-charge   OBJECT-TYPE
   SYNTAX          OCTET STRING    
   ACCESS           read-only    
   STATUS            optional   
   DESCRIPTION "The total charge for pages scanned, for this media size.
       "
::= { scanned-media-usage 5 }

-- 1.3.6.1.4.1.11.2.3.9.4.2.1.1.16.2.1.1
scanned-media-simplex-count   OBJECT-TYPE
   SYNTAX          INTEGER    
   ACCESS           read-only    
   STATUS            optional   
   DESCRIPTION "Total number of simplex pages scanned, for this media size.
       "
::= { scanned-media-usage 1 }

-- 1.3.6.1.4.1.11.2.3.9.4.2.1.1.16.2.1.2
scanned-media-simplex-charge   OBJECT-TYPE
   SYNTAX          OCTET STRING    
   ACCESS           read-write    
   STATUS            optional   
   DESCRIPTION "Charge for each simplex page printed in this media size.
       "
::= { scanned-media-usage 2 }

-- 1.3.6.1.4.1.11.2.3.9.4.2.1.1.16.2.1.3
scanned-media-duplex-count   OBJECT-TYPE
   SYNTAX          INTEGER    
   ACCESS           read-only    
   STATUS            optional   
   DESCRIPTION "Total number of duplex pages scanned, for this media size.
       "
::= { scanned-media-usage 3 }

-- 1.3.6.1.4.1.11.2.3.9.4.2.1.1.16.2.1.4
scanned-media-duplex-charge   OBJECT-TYPE
   SYNTAX          OCTET STRING    
   ACCESS           read-write    
   STATUS            optional   
   DESCRIPTION "Charge for each duplex page scanned, for this media size.
       "
::= { scanned-media-usage 4 }

-- 1.3.6.1.4.1.11.2.3.9.4.2.1.1.16.2.2
usage-scanner-total-charge   OBJECT-TYPE
   SYNTAX          OCTET STRING    
   ACCESS           read-only    
   STATUS            optional   
   DESCRIPTION "Total scanner charge or cost for all paper sizes scanned.
      "
::= { scanner-accounting 2 }


-- 1.3.6.1.4.1.11.2.3.9.4.2.1.2.2.1.89
scan-to-folder-count   OBJECT-TYPE
   SYNTAX          INTEGER    
   ACCESS           read-only    
   STATUS            optional   
   DESCRIPTION "The number of scan-to-folder scan jobs.
       "
::= { settings-scanner 89 }

-- 1.3.6.1.4.1.11.2.3.9.4.2.1.2.2.1.62
scanner-accessory-send-job-scan-count   OBJECT-TYPE
   SYNTAX          INTEGER    
   ACCESS           read-only    
   STATUS            optional   
   DESCRIPTION "This relates to the number of pages scanned for fax/send. This
   item is incremented by 2 for each sheet scanned through the ADF
   in 2-sided scan mode, and it is incremented by 1 for flatbed
   scans. Scanning for testing and calibration purposes are NOT TO
   BE INCLUDED in this count.
       "
::= { settings-scanner 62 }

-- 1.3.6.1.4.1.11.2.3.9.4.2.1.4.1.10.7
consumable-current-state   OBJECT-TYPE
   SYNTAX          INTEGER{                       cAuthLevel1(0),                      cAuthLevel2(1),                      cAuthLevel3(2),                      cAuthLevel4(3),                      cAuthLevel5(4),                      cAuthLevel6(5),                      cAuthLevel7(6),                      cGenuineHPUnsupported(8),                      cELabelDefective(9),                      cELabelMissing(10),                      cLowCondition(11),                      cOutCondition(12),                      cIncorrect(13),                      cMissing(14),                      cPastOutCondition(15),                      cConfigurableLow(16),                      cExpired(17),                      cFailure(18),                      cLeak(19),                      cUnknownManufacturer(20),                      cUnsupported(21),                      cUnavailable(22),                      cIncompatible(23),                      cStatusAreValid(31)               }   
   ACCESS           read-only    
   STATUS            optional   
   DESCRIPTION "This PML object returns the current state of the particular
   consumable. \\ 
   cAuthLevel1 - Consumable is at Authentication Level 1 \\ 
   cAuthLevel2 - Consumable is at Authentication Level 2 \\ 
   cAuthLevel3 - Consumable is at Authentication Level 3 \\ 
   cAuthLevel4 - Consumable is at Authentication Level 4 \\ 
   cAuthLevel5 - Consumable is at Authentication Level 5 \\ 
   cGenuineHPUnsupported - Cartridge is GenuineHP intended for
   another product \\ 
   cDefectiveMemory - Cartridge has a defective memory tag \\ 
   cMissingMemory - Memory tag is missing from the cartridge
										\\ 
cLowCondition - Consumable has reached the engine low
threshold \\ 
cOutCondition - Consumable has reached its out threshold \\ 
cIncorrect - Cartridge inserted is not the correct one \\ 
cMissing - Consumable is missing from the printer \\ 
cConfigurableLow - Consumable has reached the configurable
low threshold value \\ 
cStatusArevalid - The status reported on other bits are valid only if the bit is set to 1. If it is 0, the
values are invalid. \\ 
cExpired - Is the cartridge expired, which is determined \\ 
by the formatter.\\ 
cFailure - Cartridge has failed determined by the engine.																							\\ 
cLeak - Cartridge has a leak as determined by the engine.
\\cUnknownManufacturer - the brand of the cartridge is \\ 
unknown as determined by the engine. \\ 
cUnsupported --- Cartridge is not supported as determined
\\ 
by the engine. \\ 
cIncompatible - When installed consumable is incompatible with
current printer. These are the possible states and whenever the
consumable is in any of these states, the appropriate bit will
be set. The cLowCondition will be set when the consumable
reaches the engine low threshold, and cConfigurableLow will be
set when the consumable reaches the Configurable Low threshold
value. For non-cartridge supplies only cLowCondition,
cOutCondition, and cMissing will be supported.
       "
::= { consumables 7 }

-- 1.3.6.1.4.1.11.2.3.9.4.2.1.1.2.111
email-service-operational   OBJECT-TYPE
   SYNTAX          INTEGER {                       eNonOperational(1),                      eOperational(2)               }   
   ACCESS           read-only    
   STATUS            optional   
   DESCRIPTION "To check if Email service is operational on the device. Email
   is operational if email feature is enabled on the device and
   the SMTP gateway is configured.
       "
::= { status-system 111 }

-- 1.3.6.1.4.1.11.2.3.9.4.2.1.3.7.2.16
fax-billing-code-enabled   OBJECT-TYPE
   SYNTAX          INTEGER {                       
                                    eDisabled(1),                      
				     eEnabled(2)               }   
   ACCESS           read-only    
   STATUS            optional   
   DESCRIPTION "To check if Billing Code is enabled on the device for Faxes
   sent
       "
::= { status-fax-proc-sub 16 }

-- 1.3.6.1.4.1.11.2.3.9.4.2.1.3.7.2.18
fax-billing-code   OBJECT-TYPE
   SYNTAX          OCTET STRING    
   ACCESS           read-only    
   STATUS            optional   
   DESCRIPTION "The actual Billing Code applicable for Faxes sent from the
   device
       "
::= { status-fax-proc-sub 18 }

-- 1.3.6.1.4.1.11.2.3.9.4.2.1.3.7.2.17
fax-billing-code-minlength   OBJECT-TYPE
   SYNTAX          INTEGER    
   ACCESS           read-only    
   STATUS            optional   
   DESCRIPTION "The Minimum number of Billing Code digits that has to be
   specified for Faxes sent from the device. Range: 1 - 16
       "
::= { status-fax-proc-sub 17 }

-- 1.3.6.1.4.1.11.2.3.9.4.2.1.3.7.2.13
pcfax-send-enabled   OBJECT-TYPE
   SYNTAX          INTEGER {                       
                               eDisabled(1),                      
			        eEnabled(2)               }   
   ACCESS           read-only    
   STATUS            optional   
   DESCRIPTION "To check if PC Fax Send is enabled on the device. Also used by
   administrators to enable or disable PC Fax Send on the device
       "
::= { status-fax-proc-sub 13 }


-- 1.3.6.1.4.1.11.2.3.9.4.2.1.1.2.37.1.1   
background-status-msg-line1-part1   OBJECT-TYPE
   SYNTAX          OCTET STRING   
   ACCESS           read-write    
   STATUS            optional   
   DESCRIPTION " The string displayed on the device's front panel in place of
   the printer's built-in background status string. An example
   built-in background status string is '00 READY'"
::= { background-message1 1 }

-- 1.3.6.1.4.1.11.2.3.9.4.2.1.1.2.37.2.1   
background-status-msg-line2-part1   OBJECT-TYPE
   SYNTAX          OCTET STRING    
   ACCESS           read-write    
   STATUS            optional   
   DESCRIPTION " The string displayed on the device's front panel in place of
   the printer's built-in background status string. An example
   built-in background status string is '00 READY'"
::= { background-message2 1 }



-- 1.3.6.1.4.1.11.2.3.9.4.2.1.1.2.66
control-panel-key-press   OBJECT-TYPE
   SYNTAX          INTEGER    
   ACCESS           read-write    
   STATUS            optional   
   DESCRIPTION "Writing this object simulates pressing a key on the control	panel. Reading it will return the last key pressed either on the control panel or via PML. This object obsoletes/replaces CONTROL-PANEL-BUTTON-PRESS object which was unable to represent each of the possible key combinations of our current control panels (ie. Full QWERTY keyboard). The device POS will specify	the full range of keys supported by this object."
  
::= { status-system 66 }

END
