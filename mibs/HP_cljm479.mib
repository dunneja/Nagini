--  (C) COPYRIGHT HEWLETT-PACKARD COMPANY 2018.
--  
--  HP-Color-LaserJet-Pro-MFP-M479fdw Printer Model Specific MIB.
--  Version - 1.0
--  Generated on Apr. 17, 2018 .
--  
--  Company names and product names mentioned herein may be 
--  trademarks, and/or registered trademarks of their respective
--  companies.
--  
--  This MIB describes all the printer model specific
--  objects supported by the HP-Color-LaserJet-Pro-MFP-M479fdw printer
--  when networked connected.
--  
--  This MIB complies with the following dependencies:
--  
--  Printer-MIB 
--  IF-MIB 
--  SNMP-FRAMEWORK-MIB 
--  DLSW-MIB 
--  SNMP-USER-BASED-SM-MIB 
--  INET-ADDRESS-MIB 
--  HOST-RESOURCES-MIB 
--  IANA-CHARSET-MIB 
--  SNMP-TARGET-MIB 
--  SNMPv2-PARTY-MIB 
--  IEEE802dot11-MIB 
--  SNMPv2-TC 
--  IANA-PRINTER-MIB 
--  
--   

HP-COLOR-LASERJET-PRO-MFP-M479FDW-MIB          DEFINITIONS        ::=      BEGIN 

IMPORTS 
     PrtLocalizedDescriptionStringTC ,  PrtAlertSeverityLevelTC ,  PrtChannelStateTC ,  PrtSubUnitStatusTC ,  PrtConsoleDescriptionStringTC ,  PrtCapacityUnitTC ,  PrtMediaUnitTC ,  PresentOnOff ,  PrtPrintOrientationTC ,  PrtInterpreterTwoWayTC ,  PrtMarkerAddressabilityUnitTC ,  PrtMarkerColorantRoleTC ,  PrtMarkerCounterUnitTC ,  PrtMarkerSuppliesClassTC ,  PrtMarkerSuppliesSupplyUnitTC ,  PrtMediaPathMaxSpeedPrintUnitTC ,  PrtOutputPageDeliveryOrientationTC ,  PrtOutputStackingOrderTC 
        FROM Printer-MIB 
     InterfaceIndexOrZero 
        FROM IF-MIB 
     SnmpAdminString ,  SnmpEngineID 
        FROM SNMP-FRAMEWORK-MIB 
     TAddress 
        FROM DLSW-MIB 
     KeyChange 
        FROM SNMP-USER-BASED-SM-MIB 
     InetAddress 
        FROM INET-ADDRESS-MIB 
     ProductID ,  KBytes 
        FROM HOST-RESOURCES-MIB 
     IANACharset 
        FROM IANA-CHARSET-MIB 
     SnmpTagList 
        FROM SNMP-TARGET-MIB 
     StorageType ,  TAddress 
        FROM SNMPv2-PARTY-MIB 
     WEPKeytype 
        FROM IEEE802dot11-MIB 
     DisplayString ,  TruthValue ,  AutonomousType ,  PhysAddress ,  RowStatus ,  StorageType ,  TAddress ,  TDomain ,  TimeInterval ,  TimeStamp ,  RowPointer ,  TestAndIncr 
        FROM SNMPv2-TC 
     PrtAlertCodeTC ,  PrtAlertGroupTC ,  PrtAlertTrainingLevelTC ,  PrtChannelTypeTC ,  PrtCoverStatusTC ,  PrtGeneralResetTC ,  PrtInputTypeTC ,  PrtInterpreterLangFamilyTC ,  PrtMarkerMarkTechTC ,  PrtMarkerSuppliesTypeTC ,  PrtMediaPathTypeTC ,  PrtOutputTypeTC 
        FROM IANA-PRINTER-MIB; 

org                                                OBJECT IDENTIFIER               ::= { iso(1)                            3 } 
snmpV2                                             OBJECT IDENTIFIER               ::= { internet                          6 } 
private                                            OBJECT IDENTIFIER               ::= { internet                          4 } 
dod                                                OBJECT IDENTIFIER               ::= { org                               6 } 
netPML                                             OBJECT IDENTIFIER               ::= { netPeripheral                     4 } 
snmpTargetMIB                                      OBJECT IDENTIFIER               ::= { snmpModules                      12 } 
snmpModules                                        OBJECT IDENTIFIER               ::= { snmpV2                            3 } 
printmib                                           OBJECT IDENTIFIER               ::= { mib-2                            43 } 
enterprises                                        OBJECT IDENTIFIER               ::= { private                           1 } 
internet                                           OBJECT IDENTIFIER               ::= { dod                               1 } 
hpPrintServer                                      OBJECT IDENTIFIER               ::= { enterprises                      11 } 
nm-system                                          OBJECT IDENTIFIER               ::= { nm                                3 } 
ieee802dot11                                       OBJECT IDENTIFIER               ::= { 1 2 840 10036 }         
netPMLmgmt                                         OBJECT IDENTIFIER               ::= { netPML                            2 } 
snmpVacmMIB                                        OBJECT IDENTIFIER               ::= { snmpModules                      16 } 
snmpUsmMIB                                         OBJECT IDENTIFIER               ::= { snmpModules                      15 } 
trapDestination                                    OBJECT IDENTIFIER               ::= { trapDest                          2 } 
snmpTargetObjects                                  OBJECT IDENTIFIER               ::= { snmpTargetMIB                     1 } 
snmpMPDMIB                                         OBJECT IDENTIFIER               ::= { snmpModules                      11 } 
snmpFrameworkMIB                                   OBJECT IDENTIFIER               ::= { snmpModules                      10 } 
prtOutput                                          OBJECT IDENTIFIER               ::= { printmib                          9 } 
prtMediaPath                                       OBJECT IDENTIFIER               ::= { printmib                         13 } 
prtMarkerSupplies                                  OBJECT IDENTIFIER               ::= { printmib                         11 } 
prtMarkerColorant                                  OBJECT IDENTIFIER               ::= { printmib                         12 } 
prtMarker                                          OBJECT IDENTIFIER               ::= { printmib                         10 } 
prtLocalization                                    OBJECT IDENTIFIER               ::= { printmib                          7 } 
prtInterpreter                                     OBJECT IDENTIFIER               ::= { printmib                         15 } 
prtInput                                           OBJECT IDENTIFIER               ::= { printmib                          8 } 
prtCover                                           OBJECT IDENTIFIER               ::= { printmib                          6 } 
prtConsoleDisplayBuffer                            OBJECT IDENTIFIER               ::= { printmib                         16 } 
prtChannel                                         OBJECT IDENTIFIER               ::= { printmib                         14 } 
prtAlert                                           OBJECT IDENTIFIER               ::= { printmib                         18 } 
prtGeneral                                         OBJECT IDENTIFIER               ::= { printmib                          5 } 
ppmPrinter                                         OBJECT IDENTIFIER               ::= { ppmMIBObjects                     2 } 
ppmPort                                            OBJECT IDENTIFIER               ::= { ppmMIBObjects                     3 } 
ppmMIB                                             OBJECT IDENTIFIER               ::= { enterprises pwg(2699) mibs(1) ppmMIB(2) } 
interface                                          OBJECT IDENTIFIER               ::= { nm                                4 } 
mgmt                                               OBJECT IDENTIFIER               ::= { internet                          2 } 
hrDevice                                           OBJECT IDENTIFIER               ::= { host                              3 } 
nm                                                 OBJECT IDENTIFIER               ::= { hpPrintServer                     2 } 
netPeripheral                                      OBJECT IDENTIFIER               ::= { nm-system                         9 } 
source-subsystem                                   OBJECT IDENTIFIER               ::= { device                            2 } 
ieee802dot11i                                      OBJECT IDENTIFIER               ::= { ieee802dot11                      7 } 
dot11phy                                           OBJECT IDENTIFIER               ::= { ieee802dot11                      4 } 
dot11smt                                           OBJECT IDENTIFIER               ::= { ieee802dot11                      1 } 
destination-subsystem                              OBJECT IDENTIFIER               ::= { device                            4 } 
consumables                                        OBJECT IDENTIFIER               ::= { print-engine                     10 } 
device                                             OBJECT IDENTIFIER               ::= { netPMLmgmt                        1 } 
vacmViewTreeFamilyTable                            OBJECT IDENTIFIER               ::= { vacmMIBViews                      2 } 
vacmMIBObjects                                     OBJECT IDENTIFIER               ::= { snmpVacmMIB                       1 } 
vacmSecurityToGroupTable                           OBJECT IDENTIFIER               ::= { vacmMIBObjects                    2 } 
vacmContextTable                                   OBJECT IDENTIFIER               ::= { vacmMIBObjects                    1 } 
vacmAccessTable                                    OBJECT IDENTIFIER               ::= { vacmMIBObjects                    4 } 
usmUserTable                                       OBJECT IDENTIFIER               ::= { usmUser                           2 } 
usmMIBObjects                                      OBJECT IDENTIFIER               ::= { snmpUsmMIB                        1 } 
accounting                                         OBJECT IDENTIFIER               ::= { device-system                    16 } 
intrays                                            OBJECT IDENTIFIER               ::= { intray                            3 } 
trapFQDNTable                                      OBJECT IDENTIFIER               ::= { trapDest                          7 } 
trap                                               OBJECT IDENTIFIER               ::= { nm                               13 } 
trapDestinationTable                               OBJECT IDENTIFIER               ::= { trapDestination                   2 } 
snmpTargetAddrTable                                OBJECT IDENTIFIER               ::= { snmpTargetObjects                 2 } 
snmpMPDMIBObjects                                  OBJECT IDENTIFIER               ::= { snmpMPDMIB                        2 } 
snmpFrameworkMIBObjects                            OBJECT IDENTIFIER               ::= { snmpFrameworkMIB                  2 } 
prtOutputTable                                     OBJECT IDENTIFIER               ::= { prtOutput                         2 } 
prtMediaPathTable                                  OBJECT IDENTIFIER               ::= { prtMediaPath                      4 } 
prtMarkerSuppliesTable                             OBJECT IDENTIFIER               ::= { prtMarkerSupplies                 1 } 
prtMarkerColorantTable                             OBJECT IDENTIFIER               ::= { prtMarkerColorant                 1 } 
prtMarkerTable                                     OBJECT IDENTIFIER               ::= { prtMarker                         2 } 
prtLocalizationTable                               OBJECT IDENTIFIER               ::= { prtLocalization                   1 } 
prtInterpreterTable                                OBJECT IDENTIFIER               ::= { prtInterpreter                    1 } 
prtInputTable                                      OBJECT IDENTIFIER               ::= { prtInput                          2 } 
prtCoverTable                                      OBJECT IDENTIFIER               ::= { prtCover                          1 } 
prtConsoleDisplayBufferTable                       OBJECT IDENTIFIER               ::= { prtConsoleDisplayBuffer           5 } 
prtChannelTable                                    OBJECT IDENTIFIER               ::= { prtChannel                        1 } 
prtAlertTable                                      OBJECT IDENTIFIER               ::= { prtAlert                          1 } 
prtGeneralTable                                    OBJECT IDENTIFIER               ::= { prtGeneral                        1 } 
printer-color-accounting                           OBJECT IDENTIFIER               ::= { accounting                        3 } 
ppmPrinterTable                                    OBJECT IDENTIFIER               ::= { ppmPrinter                        1 } 
ppmPortTable                                       OBJECT IDENTIFIER               ::= { ppmPort                           1 } 
ppmMIBObjects                                      OBJECT IDENTIFIER               ::= { ppmMIB                            1 } 
processing-subsystem                               OBJECT IDENTIFIER               ::= { device                            3 } 
pdl                                                OBJECT IDENTIFIER               ::= { processing-subsystem              3 } 
npSecurityDot11SSIDTable                           OBJECT IDENTIFIER               ::= { npSecurity                        9 } 
npSecurityDot11EncryptedWEPKeyTable                OBJECT IDENTIFIER               ::= { npSecurity                        7 } 
npNpi                                              OBJECT IDENTIFIER               ::= { npCard                            8 } 
npCard                                             OBJECT IDENTIFIER               ::= { interface                         3 } 
npCfgAccessListTable                               OBJECT IDENTIFIER               ::= { npCfg                             9 } 
intray                                             OBJECT IDENTIFIER               ::= { print-engine                      3 } 
media-info                                         OBJECT IDENTIFIER               ::= { print-media                       3 } 
print-media                                        OBJECT IDENTIFIER               ::= { print-engine                      8 } 
ipRouteTable                                       OBJECT IDENTIFIER               ::= { ip                               21 } 
ipNetToMediaTable                                  OBJECT IDENTIFIER               ::= { ip                               22 } 
ipAddrTable                                        OBJECT IDENTIFIER               ::= { ip                               20 } 
ifMIB                                              OBJECT IDENTIFIER               ::= { mib-2                            31 } 
mib-2                                              OBJECT IDENTIFIER               ::= { mgmt                              1 } 
ifTable                                            OBJECT IDENTIFIER               ::= { interfaces                        2 } 
hrStorageTable                                     OBJECT IDENTIFIER               ::= { hrStorage                         3 } 
hrPrinterTable                                     OBJECT IDENTIFIER               ::= { hrDevice                          5 } 
host                                               OBJECT IDENTIFIER               ::= { mib-2                            25 } 
hrDiskStorageTable                                 OBJECT IDENTIFIER               ::= { hrDevice                          6 } 
hrDeviceTable                                      OBJECT IDENTIFIER               ::= { hrDevice                          2 } 
snmpAccess                                         OBJECT IDENTIFIER               ::= { nm                               15 } 
netPrinter                                         OBJECT IDENTIFIER               ::= { netPeripheral                     1 } 
npSecurityOpenSSLFIPSErrorTable                    OBJECT IDENTIFIER               ::= { npSecurity                       60 } 
scanner                                            OBJECT IDENTIFIER               ::= { source-subsystem                  2 } 
errorlog                                           OBJECT IDENTIFIER               ::= { device-system                    11 } 
quality-pdl                                        OBJECT IDENTIFIER               ::= { settings-pdl                     46 } 
dot11WEPDefaultKeysTable                           OBJECT IDENTIFIER               ::= { dot11smt                          3 } 
dot11RSNConfigAuthenticationSuitesTable            OBJECT IDENTIFIER               ::= { ieee802dot11i                     3 } 
dot11PrivacyTable                                  OBJECT IDENTIFIER               ::= { dot11smt                          5 } 
dot11StationConfigTable                            OBJECT IDENTIFIER               ::= { dot11smt                          1 } 
dot11PhyOperationTable                             OBJECT IDENTIFIER               ::= { dot11phy                          1 } 
dot11AuthenticationAlgorithmsTable                 OBJECT IDENTIFIER               ::= { dot11smt                          2 } 
print-engine                                       OBJECT IDENTIFIER               ::= { destination-subsystem             1 } 
active-print-jobs                                  OBJECT IDENTIFIER               ::= { job                               2 } 
consumables-1                                      OBJECT IDENTIFIER               ::= { consumables                       1 } 
job                                                OBJECT IDENTIFIER               ::= { device-system                     6 } 
device-system                                      OBJECT IDENTIFIER               ::= { device                            1 } 
fax-proc-sub                                       OBJECT IDENTIFIER               ::= { processing-subsystem              7 } 
vacmViewTreeFamilyEntry                            OBJECT IDENTIFIER               ::= { vacmViewTreeFamilyTable           1 } 
vacmMIBViews                                       OBJECT IDENTIFIER               ::= { vacmMIBObjects                    5 } 
vacmSecurityToGroupEntry                           OBJECT IDENTIFIER               ::= { vacmSecurityToGroupTable          1 } 
vacmContextEntry                                   OBJECT IDENTIFIER               ::= { vacmContextTable                  1 } 
vacmAccessEntry                                    OBJECT IDENTIFIER               ::= { vacmAccessTable                   1 } 
usmUser                                            OBJECT IDENTIFIER               ::= { usmMIBObjects                     2 } 
usmUserEntry                                       OBJECT IDENTIFIER               ::= { usmUserTable                      1 } 
usmStats                                           OBJECT IDENTIFIER               ::= { usmMIBObjects                     1 } 
scanner-accounting                                 OBJECT IDENTIFIER               ::= { accounting                        2 } 
printer-accounting                                 OBJECT IDENTIFIER               ::= { accounting                        1 } 
intray2                                            OBJECT IDENTIFIER               ::= { intrays                           2 } 
intray1                                            OBJECT IDENTIFIER               ::= { intrays                           1 } 
trapFQDNEntry                                      OBJECT IDENTIFIER               ::= { trapFQDNTable                     1 } 
trapDest                                           OBJECT IDENTIFIER               ::= { trap                              1 } 
trapDestinationEntry                               OBJECT IDENTIFIER               ::= { trapDestinationTable              1 } 
system                                             OBJECT IDENTIFIER               ::= { mib-2                             1 } 
snmpTargetAddrEntry                                OBJECT IDENTIFIER               ::= { snmpTargetAddrTable               1 } 
snmpMPDStats                                       OBJECT IDENTIFIER               ::= { snmpMPDMIBObjects                 1 } 
snmpEngine                                         OBJECT IDENTIFIER               ::= { snmpFrameworkMIBObjects           1 } 
snmp                                               OBJECT IDENTIFIER               ::= { mib-2                            11 } 
prtOutputEntry                                     OBJECT IDENTIFIER               ::= { prtOutputTable                    1 } 
prtMediaPathEntry                                  OBJECT IDENTIFIER               ::= { prtMediaPathTable                 1 } 
prtMarkerSuppliesEntry                             OBJECT IDENTIFIER               ::= { prtMarkerSuppliesTable            1 } 
prtMarkerColorantEntry                             OBJECT IDENTIFIER               ::= { prtMarkerColorantTable            1 } 
prtMarkerEntry                                     OBJECT IDENTIFIER               ::= { prtMarkerTable                    1 } 
prtLocalizationEntry                               OBJECT IDENTIFIER               ::= { prtLocalizationTable              1 } 
prtInterpreterEntry                                OBJECT IDENTIFIER               ::= { prtInterpreterTable               1 } 
prtInputEntry                                      OBJECT IDENTIFIER               ::= { prtInputTable                     1 } 
prtCoverEntry                                      OBJECT IDENTIFIER               ::= { prtCoverTable                     1 } 
prtConsoleDisplayBufferEntry                       OBJECT IDENTIFIER               ::= { prtConsoleDisplayBufferTable      1 } 
prtChannelEntry                                    OBJECT IDENTIFIER               ::= { prtChannelTable                   1 } 
prtAlertEntry                                      OBJECT IDENTIFIER               ::= { prtAlertTable                     1 } 
prtGeneralEntry                                    OBJECT IDENTIFIER               ::= { prtGeneralTable                   1 } 
professional-quality-pdl                           OBJECT IDENTIFIER               ::= { quality-pdl                       2 } 
printed-media-usage                                OBJECT IDENTIFIER               ::= { printer-accounting                1 } 
printed-media-color-usage                          OBJECT IDENTIFIER               ::= { printer-color-accounting          1 } 
settings-pdl                                       OBJECT IDENTIFIER               ::= { pdl                               1 } 
test                                               OBJECT IDENTIFIER               ::= { device-system                     5 } 
presentation-quality-pdl                           OBJECT IDENTIFIER               ::= { quality-pdl                       3 } 
ppmPrinterEntry                                    OBJECT IDENTIFIER               ::= { ppmPrinterTable                   1 } 
ppmPortEntry                                       OBJECT IDENTIFIER               ::= { ppmPortTable                      1 } 
ppmGeneral                                         OBJECT IDENTIFIER               ::= { ppmMIBObjects                     1 } 
pdl-postscript                                     OBJECT IDENTIFIER               ::= { pdl                               4 } 
pjl                                                OBJECT IDENTIFIER               ::= { processing-subsystem              5 } 
pdl-pcl                                            OBJECT IDENTIFIER               ::= { pdl                               3 } 
office-quality-pdl                                 OBJECT IDENTIFIER               ::= { quality-pdl                       1 } 
npWeb                                              OBJECT IDENTIFIER               ::= { npCard                           18 } 
npTcp                                              OBJECT IDENTIFIER               ::= { npCard                            6 } 
npSys                                              OBJECT IDENTIFIER               ::= { npCard                            1 } 
npSecurityDot11SSIDEntry                           OBJECT IDENTIFIER               ::= { npSecurityDot11SSIDTable          1 } 
npSecurityDot11EncryptedWEPKeyEntry                OBJECT IDENTIFIER               ::= { npSecurityDot11EncryptedWEPKeyTable    1 } 
npSecurity                                         OBJECT IDENTIFIER               ::= { npCard                           20 } 
npPort                                             OBJECT IDENTIFIER               ::= { npCard                           13 } 
npNpiPeripheralAttributeEntry                      OBJECT IDENTIFIER               ::= { npNpi                             3 } 
npIpx                                              OBJECT IDENTIFIER               ::= { npCard                           10 } 
npDhcp                                             OBJECT IDENTIFIER               ::= { npCard                           16 } 
npCtl                                              OBJECT IDENTIFIER               ::= { npCard                            7 } 
npCfg                                              OBJECT IDENTIFIER               ::= { npCard                            5 } 
npCfgAccessListEntry                               OBJECT IDENTIFIER               ::= { npCfgAccessListTable              1 } 
status-intray                                      OBJECT IDENTIFIER               ::= { intray                            2 } 
media9                                             OBJECT IDENTIFIER               ::= { media-info                        9 } 
media8                                             OBJECT IDENTIFIER               ::= { media-info                        8 } 
media7                                             OBJECT IDENTIFIER               ::= { media-info                        7 } 
media6                                             OBJECT IDENTIFIER               ::= { media-info                        6 } 
media5                                             OBJECT IDENTIFIER               ::= { media-info                        5 } 
media4                                             OBJECT IDENTIFIER               ::= { media-info                        4 } 
media34                                            OBJECT IDENTIFIER               ::= { media-info                       34 } 
media33                                            OBJECT IDENTIFIER               ::= { media-info                       33 } 
media32                                            OBJECT IDENTIFIER               ::= { media-info                       32 } 
media31                                            OBJECT IDENTIFIER               ::= { media-info                       31 } 
media30                                            OBJECT IDENTIFIER               ::= { media-info                       30 } 
media3                                             OBJECT IDENTIFIER               ::= { media-info                        3 } 
media29                                            OBJECT IDENTIFIER               ::= { media-info                       29 } 
media28                                            OBJECT IDENTIFIER               ::= { media-info                       28 } 
media27                                            OBJECT IDENTIFIER               ::= { media-info                       27 } 
media26                                            OBJECT IDENTIFIER               ::= { media-info                       26 } 
media25                                            OBJECT IDENTIFIER               ::= { media-info                       25 } 
media24                                            OBJECT IDENTIFIER               ::= { media-info                       24 } 
media23                                            OBJECT IDENTIFIER               ::= { media-info                       23 } 
media22                                            OBJECT IDENTIFIER               ::= { media-info                       22 } 
media21                                            OBJECT IDENTIFIER               ::= { media-info                       21 } 
media20                                            OBJECT IDENTIFIER               ::= { media-info                       20 } 
media2                                             OBJECT IDENTIFIER               ::= { media-info                        2 } 
media19                                            OBJECT IDENTIFIER               ::= { media-info                       19 } 
media18                                            OBJECT IDENTIFIER               ::= { media-info                       18 } 
media17                                            OBJECT IDENTIFIER               ::= { media-info                       17 } 
media16                                            OBJECT IDENTIFIER               ::= { media-info                       16 } 
media15                                            OBJECT IDENTIFIER               ::= { media-info                       15 } 
media14                                            OBJECT IDENTIFIER               ::= { media-info                       14 } 
media13                                            OBJECT IDENTIFIER               ::= { media-info                       13 } 
media12                                            OBJECT IDENTIFIER               ::= { media-info                       12 } 
media11                                            OBJECT IDENTIFIER               ::= { media-info                       11 } 
media10                                            OBJECT IDENTIFIER               ::= { media-info                       10 } 
media1                                             OBJECT IDENTIFIER               ::= { media-info                        1 } 
media-sizes                                        OBJECT IDENTIFIER               ::= { print-engine                     15 } 
settings-print-media                               OBJECT IDENTIFIER               ::= { print-media                       1 } 
max-dpi-quality-pdl                                OBJECT IDENTIFIER               ::= { quality-pdl                       4 } 
ipRouteEntry                                       OBJECT IDENTIFIER               ::= { ipRouteTable                      1 } 
ipNetToMediaEntry                                  OBJECT IDENTIFIER               ::= { ipNetToMediaTable                 1 } 
ip                                                 OBJECT IDENTIFIER               ::= { mib-2                             4 } 
ipAddrEntry                                        OBJECT IDENTIFIER               ::= { ipAddrTable                       1 } 
ifMIBObjects                                       OBJECT IDENTIFIER               ::= { ifMIB                             1 } 
interfaces                                         OBJECT IDENTIFIER               ::= { mib-2                             2 } 
ifEntry                                            OBJECT IDENTIFIER               ::= { ifTable                           1 } 
hrSystem                                           OBJECT IDENTIFIER               ::= { host                              1 } 
hrStorageEntry                                     OBJECT IDENTIFIER               ::= { hrStorageTable                    1 } 
hrPrinterEntry                                     OBJECT IDENTIFIER               ::= { hrPrinterTable                    1 } 
hrStorage                                          OBJECT IDENTIFIER               ::= { host                              2 } 
hrDiskStorageEntry                                 OBJECT IDENTIFIER               ::= { hrDiskStorageTable                1 } 
hrDeviceEntry                                      OBJECT IDENTIFIER               ::= { hrDeviceTable                     1 } 
community                                          OBJECT IDENTIFIER               ::= { snmpAccess                        1 } 
gdStatusEntry                                      OBJECT IDENTIFIER               ::= { generalDeviceStatus               2 } 
generalDeviceStatus                                OBJECT IDENTIFIER               ::= { netPrinter                        1 } 
npSecurityOpenSSLFIPSErrorEntry                    OBJECT IDENTIFIER               ::= { npSecurityOpenSSLFIPSErrorTable    1 } 
settings-fax-proc-sub                              OBJECT IDENTIFIER               ::= { fax-proc-sub                      1 } 
settings-scanner                                   OBJECT IDENTIFIER               ::= { scanner                           1 } 
error9                                             OBJECT IDENTIFIER               ::= { errorlog                          9 } 
error8                                             OBJECT IDENTIFIER               ::= { errorlog                          8 } 
error7                                             OBJECT IDENTIFIER               ::= { errorlog                          7 } 
error6                                             OBJECT IDENTIFIER               ::= { errorlog                          6 } 
error5                                             OBJECT IDENTIFIER               ::= { errorlog                          5 } 
error4                                             OBJECT IDENTIFIER               ::= { errorlog                          4 } 
error3                                             OBJECT IDENTIFIER               ::= { errorlog                          3 } 
error2                                             OBJECT IDENTIFIER               ::= { errorlog                          2 } 
error15                                            OBJECT IDENTIFIER               ::= { errorlog                         15 } 
error14                                            OBJECT IDENTIFIER               ::= { errorlog                         14 } 
error13                                            OBJECT IDENTIFIER               ::= { errorlog                         13 } 
error12                                            OBJECT IDENTIFIER               ::= { errorlog                         12 } 
error11                                            OBJECT IDENTIFIER               ::= { errorlog                         11 } 
error10                                            OBJECT IDENTIFIER               ::= { errorlog                         10 } 
error1                                             OBJECT IDENTIFIER               ::= { errorlog                          1 } 
settings-system                                    OBJECT IDENTIFIER               ::= { device-system                     1 } 
economode-quality-pdl                              OBJECT IDENTIFIER               ::= { quality-pdl                       5 } 
status-prt-eng                                     OBJECT IDENTIFIER               ::= { print-engine                      2 } 
dot11WEPDefaultKeysEntry                           OBJECT IDENTIFIER               ::= { dot11WEPDefaultKeysTable          1 } 
dot11RSNConfigAuthenticationSuitesEntry            OBJECT IDENTIFIER               ::= { dot11RSNConfigAuthenticationSuitesTable    1 } 
dot11PrivacyEntry                                  OBJECT IDENTIFIER               ::= { dot11PrivacyTable                 1 } 
dot11StationConfigEntry                            OBJECT IDENTIFIER               ::= { dot11StationConfigTable           1 } 
dot11PhyOperationEntry                             OBJECT IDENTIFIER               ::= { dot11PhyOperationTable            1 } 
dot11AuthenticationAlgorithmsEntry                 OBJECT IDENTIFIER               ::= { dot11AuthenticationAlgorithmsTable    1 } 
settings-prt-eng                                   OBJECT IDENTIFIER               ::= { print-engine                      1 } 
status-system                                      OBJECT IDENTIFIER               ::= { device-system                     2 } 
job-being-parsed                                   OBJECT IDENTIFIER               ::= { active-print-jobs                 1 } 
consumable-status                                  OBJECT IDENTIFIER               ::= { consumables-1                     1 } 
settings-job                                       OBJECT IDENTIFIER               ::= { job                               1 } 
id                                                 OBJECT IDENTIFIER               ::= { device-system                     3 } 
status-fax-proc-sub                                OBJECT IDENTIFIER               ::= { fax-proc-sub                      2 } 

afax-recv-page-count OBJECT-TYPE
        SYNTAX      INTEGER
        ACCESS      read-write
        STATUS      optional
        DESCRIPTION "Keeps the total number of pages received successfully via the
        analog fax modem. This count would be synchronised with the
        number of fax jobs received successfully. The <<hidden>>
        must be set correctly to write this object."
::= { status-fax-proc-sub 12 }

afax-send-page-count OBJECT-TYPE
        SYNTAX      INTEGER
        ACCESS      read-write
        STATUS      optional
        DESCRIPTION "Keeps the total number of pages sent successfully via the
        analog fax modem. This count would be synchronised with the
        number of fax jobs sent successfully. The <<hidden>> must
        be set correctly to write this object."
::= { status-fax-proc-sub 11 }

asset-number OBJECT-TYPE
        SYNTAX  DisplayString
        ACCESS  read-write
        STATUS  optional
        DESCRIPTION
        "User defined asset number. The POS should indicate the maximum
        supported string length. If the user entered string is too
        long, the device will store as much as possible and will return
        the <OKNearestLegal ValueSubstituted>.
        Additional information:
        The maximum supported string length is 32
        characters.  If the user entered string is too long,
        the device will store the first 32 characters and will
        return the <noError> status."
::= { id 12 }

cancel-job OBJECT-TYPE
        SYNTAX  INTEGER(0..32767)
        ACCESS  read-write
        STATUS  optional
        DESCRIPTION
        "Cancels the print job whose ID matches the value written to the
        CANCEL-JOB object. The host first learns the job ID using the
        CURRENT-JOB-PARSING-ID command. If the printer has completely
        processed the job, the printer responds with
        <badValue>. If the value of the
        CURRENT-JOB-PARSING-ID is smaller than the value written to the
        CANCEL-JOB object, then the printer responds with
        <badValue>. When read, returns the value
        of the last job ID what was canceled, or -1 to indicate no job
        has been canceled."
::= { settings-job 2 }

consumable-status-cartridge-model OBJECT-TYPE
        SYNTAX  DisplayString (SIZE(0..24))
        ACCESS  read-only
        STATUS  optional
        DESCRIPTION
        "This object is used to read the cartridge model number
        associated with this consumable.
        Additional information:
        This object will only exist for Authentic HP consumables.
        If the cartridge is deemed to be NonHP, then this object
        will not exist."
::= { consumable-status 1 }

consumable-status-first-install-date OBJECT-TYPE
        SYNTAX  DisplayString (SIZE(0..24))
        ACCESS  read-only
        STATUS  optional
        DESCRIPTION
        "This object is used to report the date on which this consumable
        was first installed. The format of the string is 'YYYYMMDD'.
        Where:
        YYYY is the year.
        MM is the month (1-12).
        DD is the day (1-31).
        The device POS needs to indicate what will be written in the
        event the printer does not have a real time clock.
        Additional information:
        This object will only exist for Authentic HP consumables.
        If the cartridge is deemed to be NonHP, then this object
        will not exist. For printers without internal clocks, the
        date will always be 20000101."
::= { consumable-status 8 }

consumable-status-manufacturing-date OBJECT-TYPE
        SYNTAX  DisplayString (SIZE(0..24))
        ACCESS  read-only
        STATUS  optional
        DESCRIPTION
        "This object is used to report the date on which this consumable
        was manufactured. The format of the string is 'YYYYMMDD', where
        YYYY is the year, MM is the month (1-12), and DD is the day
        (1-31).
        Additional information:
        This object will only exist for Authentic HP consumables.
        If the cartridge is deemed to be NonHP, then this object
        will not exist."
::= { consumable-status 2 }

consumable-status-manufacturing-signature OBJECT-TYPE
        SYNTAX		OCTET STRING
        ACCESS		read-only
        STATUS		optional
        DESCRIPTION
        "This object reurns the digital signature written to the
        consumable during manufacturing. The interpretation of the
        signature is determined by the printer model,cartridge model
        and cartridge manufacturing date.The actual interpretation is
        performed by the online cartridge verification service. The
        data is encoded most significant octet first. A manufacturing
        signature consisting of a single byte indicates the error: 0x01
        : The digital signature is not currently available, but should
        be available at some point in the future.The client should try
        again in future. 0x02 : The digital signature was not able to
        be retrieved from the cartridge because an error occured during
        retrieval. 0x03 : The digital signature is not supported by the
        currently installed cartridge. The format of the binary payload
        is dependent on the printer model, cartridge model and
        cartridge manufacturing date.Clients consuming this information
        must know the format for the printer in question."
::= { consumable-status 104 }

consumable-status-serial-number OBJECT-TYPE
        SYNTAX  DisplayString (SIZE(0..24))
        ACCESS  read-only
        STATUS  optional
        DESCRIPTION
        "This object is used to report the serial number for this
        consumable.
        Additional information:
        This object will only exist for Authentic HP consumables.
        If the cartridge is deemed to be NonHP, then this object
        will not exist."
::= { consumable-status 3 }

current-job-parsing-id OBJECT-TYPE
        SYNTAX  INTEGER(-1..2147483647)
        ACCESS  read-only
        STATUS  optional
        DESCRIPTION
        "Contains the printer assigned job identification for the job
        currently being processed by the processing PDL sub-system. The
        job ID is a monotonically increasing number. The job ID may be
        reset to zero at power-up and may roll over to zero after
        reaching some maximum value.
        Additional information:
        A value of -1 is returned when the printer
        is not parsing a job."
::= { job-being-parsed 1 }

date-and-time OBJECT-TYPE
        SYNTAX      OCTET STRING
        ACCESS      read-write
        STATUS      optional
        DESCRIPTION "A C structure containing the following fields:    typedef
        struct {
        ubyte yr; /* year: 0 to 99 */
        ubyte mon; /* month: 1 to 12 */
        ubyte day; /* day: 1 to 31 */
        ubyte wday; /* Day of week: 1 to 07 */
        ubyte hr; /* hour: 0 to 23 */
        ubyte min; /* minute: 0 to 59 */
        ubyte sec; /* second: 0 to 59 */
        } date_t;
        where ubyte is an unsigned byte (0-255)."
::= { status-system 17 }

device-default-duplex-standard		OBJECT-TYPE
        SYNTAX	INTEGER
        ACCESS	read-only
        STATUS	optional
        DESCRIPTION "Indicates whether or not the printer supports EPEAT GOLD or EuP
        Lot4 standards."
::= { settings-prt-eng 43 }

device-location OBJECT-TYPE
        SYNTAX  DisplayString
        ACCESS  read-write
        STATUS  optional
        DESCRIPTION
        "User defined device location. The POS should indicate the
        maximum supported string length. If the user entered string is
        too long, the device will store as much as possible and will
        return the <OKNearestLegal ValueSubstituted>.
        Additional information:
        The maximum supported string length is 32
        characters.  If the user entered string is too long,
        the device will store the first 32 characters and will
        return the <noError> status."
::= { id 11 }

device-name OBJECT-TYPE
        SYNTAX  DisplayString (SIZE(0..32))
        ACCESS  read-write
        STATUS  optional
        DESCRIPTION
        "User defined device name. The POS should indicate the maximum
        supported string length. If the user entered string is too
        long, the device will store as much as possible and will return
        the <OKNearestLegal ValueSubstituted>.
        Additional information:
        The maximum supported string length is 32
        characters.  If the user entered string is too long,
        the device will store the first 32 characters and will
        return the <noError> status."
::= { id 10 }

dot11AuthenticationAlgorithm OBJECT-TYPE
        SYNTAX INTEGER { openSystem (1), sharedKey (2) }
        MAX-ACCESS read-only
        STATUS current
        DESCRIPTION
        "This attribute shall be a set of all the authentication
        algorithms supported by the STAs. The following are the
        default values and the associated algorithm.
        Value = 1: Open System
        Value = 2: Shared Key"
::= { dot11AuthenticationAlgorithmsEntry 2 }

dot11AuthenticationAlgorithmsEnable OBJECT-TYPE
        SYNTAX TruthValue
        MAX-ACCESS read-write
        STATUS current
        DESCRIPTION
        "This attribute, when true at a station,
        shall enable the acceptance of the authentication
        algorithm described in the corresponding table
        entry in authentication frames received by the
        station that have odd authentication sequence numbers.
        The default value of this attribute shall be 1 for
        the Open System table entry and 2 for all other table entries."
::= { dot11AuthenticationAlgorithmsEntry 3 }

dot11CurrentRegDomain OBJECT-TYPE
        --   SYNTAX Integer32
        SYNTAX INTEGER {fcc(16),
        doc(32),
        etsi(48),
        spain (49),
        france(50),
        mkk (64),
        japan (65) }
        MAX-ACCESS read-write
        STATUS current
        DESCRIPTION
        "The current regulatory domain this instance of the PMD is
        supporting. This object corresponds to one of the
        RegDomains listed in dot11RegDomainsSupported."
::= { dot11PhyOperationEntry 2 }

dot11DesiredBSSType OBJECT-TYPE
        SYNTAX INTEGER { infrastructure(1), independent(2), any(3) }
        MAX-ACCESS read-write
        STATUS current
        DESCRIPTION
        "This attribute shall specify the type of BSS the
        station shall use when scanning for a BSS with which
        to synchronize. This value is used to filter Probe
        Response frames and Beacons. When set to infrastructure,
        the station shall only synchronize with a BSS whose
        Capability Information field has the ESS subfield set
        to 1. When set to independent, the station shall only
        synchronize with a BSS whose Capability Information
        field has the IBSS subfield set to 1. When set to
        any, the station may synchronize to either type of
        BSS."
::= { dot11StationConfigEntry 10 }

dot11DesiredSSID OBJECT-TYPE
        SYNTAX OCTET STRING (SIZE(0..32))
        MAX-ACCESS read-write
        STATUS current
        DESCRIPTION
        "This attribute reflects the Service Set ID used
        in the DesiredSSID parameter of the most recent
        MLME_Scan.request. This value may be modified
        by an external management entity and used by the
        local SME to make decisions about the Scanning process."
::= { dot11StationConfigEntry 9 }

dot11PrivacyInvoked OBJECT-TYPE
        SYNTAX TruthValue
        MAX-ACCESS read-write
        STATUS current
        DESCRIPTION
        "When this attribute is true, it shall indicate that the IEEE
        802.11 WEP mechanism is used for transmitting frames of type
        Data. The default value of this attribute shall be false."
::= { dot11PrivacyEntry 1 }

dot11RSNConfigAuthenticationSuite OBJECT-TYPE
        SYNTAX		OCTET STRING (SIZE(4))
        MAX-ACCESS	read-only
        STATUS		current
        DESCRIPTION
        "An authentication suite. Note that dot1X and PSK may
        not be enabled simultaneously. These are mutually exclusive.
        The first three octets shall form an OUI and the fourth octet a
        cipher/authentication suite within that OUI space.
        00:00:00:1 is dot1X,
        00:00:00:2 is PSK"
::= { dot11RSNConfigAuthenticationSuitesEntry 2 }

dot11RSNConfigAuthenticationSuiteEnabled OBJECT-TYPE
        SYNTAX		TruthValue
        MAX-ACCESS	read-write
        STATUS		current
        DESCRIPTION
        "This variable indicates whether the corresponding
        authentication suite is enabled/disabled."
::= { dot11RSNConfigAuthenticationSuitesEntry 3 }

dot11WEPDefaultKeyID OBJECT-TYPE
        SYNTAX INTEGER (0..3)
        MAX-ACCESS read-write
        STATUS current
        DESCRIPTION
        "This attribute shall indicate the use of the first,
        second, third, or fourth element of the WEPDefaultKeys
        array when set to values of zero, one, two, or three. The
        default value of this attribute shall be 0."
        REFERENCE "ISO/IEC 8802-11:1999, 8.3.2"
::= { dot11PrivacyEntry 2 }

dot11WEPDefaultKeyValue OBJECT-TYPE
        SYNTAX WEPKeytype
        MAX-ACCESS read-write
        STATUS current
        DESCRIPTION
        "A WEP default secret key value."
::= { dot11WEPDefaultKeysEntry 2 }

duplex-page-count OBJECT-TYPE
        SYNTAX  INTEGER
        ACCESS  read-only
        STATUS  optional
        DESCRIPTION
        "Total number of sheets of media that have been duplex printed.
        A sheet is counted if it travels through the duplex page path,
        regardless of whether or not marks are made on the page. The
        POS will indicate if the value is kept in NVRAM."
::= { status-prt-eng 22 }

economode-quality-pdl-display-tag		OBJECT-TYPE
        SYNTAX     INTEGER {
        cLaserQualityNormalMode(1000),
        cLaserQualityBestMode(1002),
        cLaserQualityDraftMode(1003),
        cLaserQualityMaximumMode(1004),
        cLaserQualityEconoMode(1005),
        cInkQualityDraftMode(3000),
        cInkQualityNormalMode(3001),
        cInkQualityBestMode(3002),
        cInkQualityMaximumMode(3003)
        }
        ACCESS     read-only
        STATUS      optional
        DESCRIPTION "Returns an Enum corresponding to the Description used by the client to provide a display string of quality attributes associated with economode Quality."
::= { economode-quality-pdl 3 }

economode-quality-pdl-hint-tag		OBJECT-TYPE
        SYNTAX     INTEGER {
        cLaserQualityNormalColorHint(2000),
        cLaserQualityNormalMonoHint(2001),
        cLaserQualityBestHint(2002),
        cLaserQualityDraftHint(2003),
        cLaserQualityMaximumHint(2004),
        cLaserQualityEconoHint(2005),
        cInkQualityDraftHint(4000),
        cInkQualityNormalHint(4005),
        cInkQualityBestHint(4010),
        cInkQualityMaximumHint(4015)
        }
        ACCESS     read-only
        STATUS     optional
        DESCRIPTION " Returns an Enum corresponding to the Description used by the client to provide underlying technology behind print quality such as ImageREt."
::= { economode-quality-pdl 2 }

economode-quality-pdl-optimum-resolution		OBJECT-TYPE
        SYNTAX     INTEGER {
        e150(1),
        e300(2),
        e600(3),
        e1200(4)
        }
        ACCESS     read-only
        STATUS     optional
        DESCRIPTION "Indicates the current DPI option selected for the economode quality draft.
        Reference resolution at the bottom of the mib for latest enumeration information."
::= { economode-quality-pdl 1 }

enable-engine-early-warmup OBJECT-TYPE
        SYNTAX     INTEGER {
        eDisable(1),
        eEnable(2)
        }
        ACCESS     read-write
        STATUS      optional
        DESCRIPTION "This PML object is used by HP SW to enable/disable the printer
        to send the signal of warm-up process early to engine. The
        effect of warming up early will reduce the First Page Out
        time."
::= { settings-system 101 }

encryption-password-max-length OBJECT-TYPE
        SYNTAX  INTEGER
        ACCESS  read-write
        STATUS  optional
        DESCRIPTION
        "This Object will allow the Customer to query for the max
        password length of a secure encrypted job supported by the
        device. Its value will be set to 12 for 4-line devices and 32
        for all others."
::= { settings-job 16 }

encryption-password-min-length OBJECT-TYPE
        SYNTAX  INTEGER
        ACCESS  read-write
        STATUS  optional
        DESCRIPTION
        "This Object will allow the Customer to query for the min
        password length of a secure encrypted job supported by the
        device. Its value will be set to 4."
::= { settings-job 17 }

encryption-password-type OBJECT-TYPE
        SYNTAX  INTEGER {
        eFalse(0),
        eTrue(1)
        }
        ACCESS  read-write
        STATUS  optional
        DESCRIPTION
        "This Object will allow the Customer to query for the supported
        encryption type. Its value will be set to AlphaNumeric (Value
        as 1) if password can be alphanumeric and Numeric (Value as 0)
        otherwise."
::= { settings-job 15 }

energy-star OBJECT-TYPE
        SYNTAX  INTEGER
        ACCESS  read-write
        STATUS  optional
        DESCRIPTION
        "Returns or changes the Energy Star sleep value. If the value
        is greater than zero, then the device will go into energy
        saving sleep mode after the print engine has been idle for the
        number of seconds specified by this object. A value of zero
        means Energy Star is disabled and the device will not go to
        sleep based on print engine idle time. The value must be
        non-negative."
::= { settings-system 1 }

error1-code OBJECT-TYPE
        SYNTAX  INTEGER
        ACCESS  read-only
        STATUS  optional
        DESCRIPTION
        "Contains a device specific error code. Each device POS should
        list what errors are logged to the error log and the meaning of
        each supported error code value."
::= { error1 2 }

error1-date-time OBJECT-TYPE
        SYNTAX      OCTET STRING
        ACCESS      read-only
        STATUS      optional
        DESCRIPTION "This item contains the date and the time at which an error
        occurred. The values returned will be in hexadecimal. If the
        date is 2004-Jul-13 and the time is 03:15 a.m., we get 04 07 0d
        03 0f where,
        04 (hex) - corresponds to the year 2004.
        07 (hex) - corresponds to month, 07
        0d (hex) - corresponds to date, 13
        03 (hex) - corresponds to hour, 3 a.m.
        0f (hex) - corresponds to min, 15."
::= { error1 3 }

error1-time-stamp OBJECT-TYPE
        SYNTAX  INTEGER
        ACCESS  read-only
        STATUS  optional
        DESCRIPTION
        "Contains some sort of time stamp indicating when error 1
        occurred. Example time stamps include the actual time the error
        occurred (in seconds since Jan. 1, 1970), and the total engine
        page count. The device POS documents the meaning of the time
        stamp."
::= { error1 1 }

error10-code OBJECT-TYPE
        SYNTAX  INTEGER
        ACCESS  read-only
        STATUS  optional
        DESCRIPTION
        "Contains a device specific error code. Each device POS should
        list what errors are logged to the error log and the meaning of
        each supported error code value."
::= { error10 2 }

error10-date-time OBJECT-TYPE
        SYNTAX      OCTET STRING
        ACCESS      read-only
        STATUS      optional
        DESCRIPTION "This item contains the date and the time at which an error
        occurred. The values returned will be in hexadecimal. If the
        date is 2004-Jul-13 and the time is 03:15 a.m., we get 04 07 0d
        03 0f where,
        04 (hex) - corresponds to the year 2004.
        07 (hex) - corresponds to month, 07
        0d (hex) - corresponds to date, 13
        03 (hex) - corresponds to hour, 3 a.m.
        0f (hex) - corresponds to min, 15."
::= { error10 3 }

error10-time-stamp OBJECT-TYPE
        SYNTAX  INTEGER
        ACCESS  read-only
        STATUS  optional
        DESCRIPTION
        "Contains some sort of time stamp indicating when error 10
        occurred. Example time stamps include the actual time the error
        occurred (in seconds since Jan. 1, 1970), and the total engine
        page count. The device POS documents the meaning of the time
        stamp."
::= { error10 1 }

error11-code OBJECT-TYPE
        SYNTAX  INTEGER
        ACCESS  read-only
        STATUS  optional
        DESCRIPTION
        "Contains a device specific error code. Each device POS should
        list what errors are logged to the error log and the meaning of
        each supported error code value."
::= { error11 2 }

error11-date-time OBJECT-TYPE
        SYNTAX      OCTET STRING
        ACCESS      read-only
        STATUS      optional
        DESCRIPTION "This item contains the date and the time at which an error
        occurred. The values returned will be in hexadecimal. If the
        date is 2004-Jul-13 and the time is 03:15 a.m., we get 04 07 0d
        03 0f where,
        04 (hex) - corresponds to the year 2004.
        07 (hex) - corresponds to month, 07
        0d (hex) - corresponds to date, 13
        03 (hex) - corresponds to hour, 3 a.m.
        0f (hex) - corresponds to min, 15."
::= { error11 3 }

error11-time-stamp OBJECT-TYPE
        SYNTAX  INTEGER
        ACCESS  read-only
        STATUS  optional
        DESCRIPTION
        "Contains some sort of time stamp indicating when error 11
        occurred. Example time stamps include the actual time the error
        occurred (in seconds since Jan. 1, 1970), and the total engine
        page count. The device POS documents the meaning of the time
        stamp."
::= { error11 1 }

error12-code OBJECT-TYPE
        SYNTAX  INTEGER
        ACCESS  read-only
        STATUS  optional
        DESCRIPTION
        "Contains a device specific error code. Each device POS should
        list what errors are logged to the error log and the meaning of
        each supported error code value."
::= { error12 2 }

error12-date-time OBJECT-TYPE
        SYNTAX      OCTET STRING
        ACCESS      read-only
        STATUS      optional
        DESCRIPTION "This item contains the date and the time at which an error
        occurred. The values returned will be in hexadecimal. If the
        date is 2004-Jul-13 and the time is 03:15 a.m., we get 04 07 0d
        03 0f where,
        04 (hex) - corresponds to the year 2004.
        07 (hex) - corresponds to month, 07
        0d (hex) - corresponds to date, 13
        03 (hex) - corresponds to hour, 3 a.m.
        0f (hex) - corresponds to min, 15."
::= { error12 3 }

error12-time-stamp OBJECT-TYPE
        SYNTAX  INTEGER
        ACCESS  read-only
        STATUS  optional
        DESCRIPTION
        "Contains some sort of time stamp indicating when error 12
        occurred. Example time stamps include the actual time the error
        occurred (in seconds since Jan. 1, 1970), and the total engine
        page count. The device POS documents the meaning of the time
        stamp."
::= { error12 1 }

error13-code OBJECT-TYPE
        SYNTAX  INTEGER
        ACCESS  read-only
        STATUS  optional
        DESCRIPTION
        "Contains a device specific error code. Each device POS should
        list what errors are logged to the error log and the meaning of
        each supported error code value."
::= { error13 2 }

error13-date-time OBJECT-TYPE
        SYNTAX      OCTET STRING
        ACCESS      read-only
        STATUS      optional
        DESCRIPTION "This item contains the date and the time at which an error
        occurred. The values returned will be in hexadecimal. If the
        date is 2004-Jul-13 and the time is 03:15 a.m., we get 04 07 0d
        03 0f where,
        04 (hex) - corresponds to the year 2004.
        07 (hex) - corresponds to month, 07
        0d (hex) - corresponds to date, 13
        03 (hex) - corresponds to hour, 3 a.m.
        0f (hex) - corresponds to min, 15."
::= { error13 3 }

error13-time-stamp OBJECT-TYPE
        SYNTAX  INTEGER
        ACCESS  read-only
        STATUS  optional
        DESCRIPTION
        "Contains some sort of time stamp indicating when error 13
        occurred. Example time stamps include the actual time the error
        occurred (in seconds since Jan. 1, 1970), and the total engine
        page count. The device POS documents the meaning of the time
        stamp."
::= { error13 1 }

error14-code OBJECT-TYPE
        SYNTAX  INTEGER
        ACCESS  read-only
        STATUS  optional
        DESCRIPTION
        "Contains a device specific error code. Each device POS should
        list what errors are logged to the error log and the meaning of
        each supported error code value."
::= { error14 2 }

error14-date-time OBJECT-TYPE
        SYNTAX      OCTET STRING
        ACCESS      read-only
        STATUS      optional
        DESCRIPTION "This item contains the date and the time at which an error
        occurred. The values returned will be in hexadecimal. If the
        date is 2004-Jul-13 and the time is 03:15 a.m., we get 04 07 0d
        03 0f where,
        04 (hex) - corresponds to the year 2004.
        07 (hex) - corresponds to month, 07
        0d (hex) - corresponds to date, 13
        03 (hex) - corresponds to hour, 3 a.m.
        0f (hex) - corresponds to min, 15."
::= { error14 3 }

error14-time-stamp OBJECT-TYPE
        SYNTAX  INTEGER
        ACCESS  read-only
        STATUS  optional
        DESCRIPTION
        "Contains some sort of time stamp indicating when error 14
        occurred. Example time stamps include the actual time the error
        occurred (in seconds since Jan. 1, 1970), and the total engine
        page count. The device POS documents the meaning of the time
        stamp."
::= { error14 1 }

error15-code OBJECT-TYPE
        SYNTAX  INTEGER
        ACCESS  read-only
        STATUS  optional
        DESCRIPTION
        "Contains a device specific error code. Each device POS should
        list what errors are logged to the error log and the meaning of
        each supported error code value."
::= { error15 2 }

error15-date-time OBJECT-TYPE
        SYNTAX      OCTET STRING
        ACCESS      read-only
        STATUS      optional
        DESCRIPTION "This item contains the date and the time at which an error
        occurred. The values returned will be in hexadecimal. If the
        date is 2004-Jul-13 and the time is 03:15 a.m., we get 04 07 0d
        03 0f where,
        04 (hex) - corresponds to the year 2004.
        07 (hex) - corresponds to month, 07
        0d (hex) - corresponds to date, 13
        03 (hex) - corresponds to hour, 3 a.m.
        0f (hex) - corresponds to min, 15."
::= { error15 3 }

error15-time-stamp OBJECT-TYPE
        SYNTAX  INTEGER
        ACCESS  read-only
        STATUS  optional
        DESCRIPTION
        "Contains some sort of time stamp indicating when error 15
        occurred. Example time stamps include the actual time the error
        occurred (in seconds since Jan. 1, 1970), and the total engine
        page count. The device POS documents the meaning of the time
        stamp."
::= { error15 1 }

error2-code OBJECT-TYPE
        SYNTAX  INTEGER
        ACCESS  read-only
        STATUS  optional
        DESCRIPTION
        "Contains a device specific error code. Each device POS should
        list what errors are logged to the error log and the meaning of
        each supported error code value."
::= { error2 2 }

error2-date-time OBJECT-TYPE
        SYNTAX      OCTET STRING
        ACCESS      read-only
        STATUS      optional
        DESCRIPTION "This item contains the date and the time at which an error
        occurred. The values returned will be in hexadecimal. If the
        date is 2004-Jul-13 and the time is 03:15 a.m., we get 04 07 0d
        03 0f where,
        04 (hex) - corresponds to the year 2004.
        07 (hex) - corresponds to month, 07
        0d (hex) - corresponds to date, 13
        03 (hex) - corresponds to hour, 3 a.m.
        0f (hex) - corresponds to min, 15."
::= { error2 3 }

error2-time-stamp OBJECT-TYPE
        SYNTAX  INTEGER
        ACCESS  read-only
        STATUS  optional
        DESCRIPTION
        "Contains some sort of time stamp indicating when error 2
        occurred. Example time stamps include the actual time the error
        occurred (in seconds since Jan. 1, 1970), and the total engine
        page count. The device POS documents the meaning of the time
        stamp."
::= { error2 1 }

error3-code OBJECT-TYPE
        SYNTAX  INTEGER
        ACCESS  read-only
        STATUS  optional
        DESCRIPTION
        "Contains a device specific error code. Each device POS should
        list what errors are logged to the error log and the meaning of
        each supported error code value."
::= { error3 2 }

error3-date-time OBJECT-TYPE
        SYNTAX      OCTET STRING
        ACCESS      read-only
        STATUS      optional
        DESCRIPTION "This item contains the date and the time at which an error
        occurred. The values returned will be in hexadecimal. If the
        date is 2004-Jul-13 and the time is 03:15 a.m., we get 04 07 0d
        03 0f where,
        04 (hex) - corresponds to the year 2004.
        07 (hex) - corresponds to month, 07
        0d (hex) - corresponds to date, 13
        03 (hex) - corresponds to hour, 3 a.m.
        0f (hex) - corresponds to min, 15."
::= { error3 3 }

error3-time-stamp OBJECT-TYPE
        SYNTAX  INTEGER
        ACCESS  read-only
        STATUS  optional
        DESCRIPTION
        "Contains some sort of time stamp indicating when error 3
        occurred. Example time stamps include the actual time the error
        occurred (in seconds since Jan. 1, 1970), and the total engine
        page count. The device POS documents the meaning of the time
        stamp."
::= { error3 1 }

error4-code OBJECT-TYPE
        SYNTAX  INTEGER
        ACCESS  read-only
        STATUS  optional
        DESCRIPTION
        "Contains a device specific error code. Each device POS should
        list what errors are logged to the error log and the meaning of
        each supported error code value."
::= { error4 2 }

error4-date-time OBJECT-TYPE
        SYNTAX      OCTET STRING
        ACCESS      read-only
        STATUS      optional
        DESCRIPTION "This item contains the date and the time at which an error
        occurred. The values returned will be in hexadecimal. If the
        date is 2004-Jul-13 and the time is 03:15 a.m., we get 04 07 0d
        03 0f where,
        04 (hex) - corresponds to the year 2004.
        07 (hex) - corresponds to month, 07
        0d (hex) - corresponds to date, 13
        03 (hex) - corresponds to hour, 3 a.m.
        0f (hex) - corresponds to min, 15."
::= { error4 3 }

error4-time-stamp OBJECT-TYPE
        SYNTAX  INTEGER
        ACCESS  read-only
        STATUS  optional
        DESCRIPTION
        "Contains some sort of time stamp indicating when error 4
        occurred. Example time stamps include the actual time the error
        occurred (in seconds since Jan. 1, 1970), and the total engine
        page count. The device POS documents the meaning of the time
        stamp."
::= { error4 1 }

error5-code OBJECT-TYPE
        SYNTAX  INTEGER
        ACCESS  read-only
        STATUS  optional
        DESCRIPTION
        "Contains a device specific error code. Each device POS should
        list what errors are logged to the error log and the meaning of
        each supported error code value."
::= { error5 2 }

error5-date-time OBJECT-TYPE
        SYNTAX      OCTET STRING
        ACCESS      read-only
        STATUS      optional
        DESCRIPTION "This item contains the date and the time at which an error
        occurred. The values returned will be in hexadecimal. If the
        date is 2004-Jul-13 and the time is 03:15 a.m., we get 04 07 0d
        03 0f where,
        04 (hex) - corresponds to the year 2004.
        07 (hex) - corresponds to month, 07
        0d (hex) - corresponds to date, 13
        03 (hex) - corresponds to hour, 3 a.m.
        0f (hex) - corresponds to min, 15."
::= { error5 3 }

error5-time-stamp OBJECT-TYPE
        SYNTAX  INTEGER
        ACCESS  read-only
        STATUS  optional
        DESCRIPTION
        "Contains some sort of time stamp indicating when error 5
        occurred. Example time stamps include the actual time the error
        occurred (in seconds since Jan. 1, 1970), and the total engine
        page count. The device POS documents the meaning of the time
        stamp."
::= { error5 1 }

error6-code OBJECT-TYPE
        SYNTAX  INTEGER
        ACCESS  read-only
        STATUS  optional
        DESCRIPTION
        "Contains a device specific error code. Each device POS should
        list what errors are logged to the error log and the meaning of
        each supported error code value."
::= { error6 2 }

error6-date-time OBJECT-TYPE
        SYNTAX      OCTET STRING
        ACCESS      read-only
        STATUS      optional
        DESCRIPTION "This item contains the date and the time at which an error
        occurred. The values returned will be in hexadecimal. If the
        date is 2004-Jul-13 and the time is 03:15 a.m., we get 04 07 0d
        03 0f where,
        04 (hex) - corresponds to the year 2004.
        07 (hex) - corresponds to month, 07
        0d (hex) - corresponds to date, 13
        03 (hex) - corresponds to hour, 3 a.m.
        0f (hex) - corresponds to min, 15."
::= { error6 3 }

error6-time-stamp OBJECT-TYPE
        SYNTAX  INTEGER
        ACCESS  read-only
        STATUS  optional
        DESCRIPTION
        "Contains some sort of time stamp indicating when error 6
        occurred. Example time stamps include the actual time the error
        occurred (in seconds since Jan. 1, 1970), and the total engine
        page count. The device POS documents the meaning of the time
        stamp."
::= { error6 1 }

error7-code OBJECT-TYPE
        SYNTAX  INTEGER
        ACCESS  read-only
        STATUS  optional
        DESCRIPTION
        "Contains a device specific error code. Each device POS should
        list what errors are logged to the error log and the meaning of
        each supported error code value."
::= { error7 2 }

error7-date-time OBJECT-TYPE
        SYNTAX      OCTET STRING
        ACCESS      read-only
        STATUS      optional
        DESCRIPTION "This item contains the date and the time at which an error
        occurred. The values returned will be in hexadecimal. If the
        date is 2004-Jul-13 and the time is 03:15 a.m., we get 04 07 0d
        03 0f where,
        04 (hex) - corresponds to the year 2004.
        07 (hex) - corresponds to month, 07
        0d (hex) - corresponds to date, 13
        03 (hex) - corresponds to hour, 3 a.m.
        0f (hex) - corresponds to min, 15."
::= { error7 3 }

error7-time-stamp OBJECT-TYPE
        SYNTAX  INTEGER
        ACCESS  read-only
        STATUS  optional
        DESCRIPTION
        "Contains some sort of time stamp indicating when error 7
        occurred. Example time stamps include the actual time the error
        occurred (in seconds since Jan. 1, 1970), and the total engine
        page count. The device POS documents the meaning of the time
        stamp."
::= { error7 1 }

error8-code OBJECT-TYPE
        SYNTAX  INTEGER
        ACCESS  read-only
        STATUS  optional
        DESCRIPTION
        "Contains a device specific error code. Each device POS should
        list what errors are logged to the error log and the meaning of
        each supported error code value."
::= { error8 2 }

error8-date-time OBJECT-TYPE
        SYNTAX      OCTET STRING
        ACCESS      read-only
        STATUS      optional
        DESCRIPTION "This item contains the date and the time at which an error
        occurred. The values returned will be in hexadecimal. If the
        date is 2004-Jul-13 and the time is 03:15 a.m., we get 04 07 0d
        03 0f where,
        04 (hex) - corresponds to the year 2004.
        07 (hex) - corresponds to month, 07
        0d (hex) - corresponds to date, 13
        03 (hex) - corresponds to hour, 3 a.m.
        0f (hex) - corresponds to min, 15."
::= { error8 3 }

error8-time-stamp OBJECT-TYPE
        SYNTAX  INTEGER
        ACCESS  read-only
        STATUS  optional
        DESCRIPTION
        "Contains some sort of time stamp indicating when error 8
        occurred. Example time stamps include the actual time the error
        occurred (in seconds since Jan. 1, 1970), and the total engine
        page count. The device POS documents the meaning of the time
        stamp."
::= { error8 1 }

error9-code OBJECT-TYPE
        SYNTAX  INTEGER
        ACCESS  read-only
        STATUS  optional
        DESCRIPTION
        "Contains a device specific error code. Each device POS should
        list what errors are logged to the error log and the meaning of
        each supported error code value."
::= { error9 2 }

error9-date-time OBJECT-TYPE
        SYNTAX      OCTET STRING
        ACCESS      read-only
        STATUS      optional
        DESCRIPTION "This item contains the date and the time at which an error
        occurred. The values returned will be in hexadecimal. If the
        date is 2004-Jul-13 and the time is 03:15 a.m., we get 04 07 0d
        03 0f where,
        04 (hex) - corresponds to the year 2004.
        07 (hex) - corresponds to month, 07
        0d (hex) - corresponds to date, 13
        03 (hex) - corresponds to hour, 3 a.m.
        0f (hex) - corresponds to min, 15."
::= { error9 3 }

error9-time-stamp OBJECT-TYPE
        SYNTAX  INTEGER
        ACCESS  read-only
        STATUS  optional
        DESCRIPTION
        "Contains some sort of time stamp indicating when error 9
        occurred. Example time stamps include the actual time the error
        occurred (in seconds since Jan. 1, 1970), and the total engine
        page count. The device POS documents the meaning of the time
        stamp."
::= { error9 1 }

fax-job-scan-count OBJECT-TYPE
        SYNTAX      INTEGER(0..9999999)
        ACCESS      read-only
        STATUS      optional
        DESCRIPTION "The number of fax scan jobs."
::= { settings-scanner 90 }

fax-print-page-count OBJECT-TYPE
        SYNTAX     INTEGER
        ACCESS     read-write
        STATUS      optional
        DESCRIPTION "This object tracks the page count for the pages sent to the
        print engine for fax jobs. In order to write this object
        SERVICE-PASSWORD must be set correctly."
::= { settings-fax-proc-sub 32 }

fipsErrorCode				OBJECT-TYPE
        SYNTAX			INTEGER
        MAX-ACCESS              read-only
        STATUS			current
        DESCRIPTION "This is a bit mask indicating the errors encountered on the corresponding interface.
        BIT 0 - SNMPV3 account configured with non FIPS-140 Algorithm (either MD5 or DES)
        BIT 1 - Kerberos configured with non FIPS-140 Algorithm (either MD5 or DES)
        BIT 2 - ID certificate has non FIPS-140 Algorithm (signature created using MD2/MD4/MD5)
        BIT 3 - CA certificate has non FIPS-140 Algorithm (signature created using MD2/MD4/MD5)
        BIT 4 - NONE of the TLS protocols are Enabled. At least one protocol has to be enabled.
        BIT 5 - The Encryption Strength selected does not comply with FIPS-140. Only HIGH is supported.
        BIT 6 - The selected cipher list contains invalid combination for the TLS protocol selected/configured.
        "
::= {  npSecurityOpenSSLFIPSErrorEntry  2  }

fipsifIndex					OBJECT-TYPE
        SYNTAX			INTEGER
        MAX-ACCESS              read-only
        STATUS			current
        DESCRIPTION "Specifies the interface number.
        Note: As of now this table will have just one row as each JDI image supports
        just one network interface. In the near future, JDI will support multiple network
        interfaces and each row will correspond to a separate interface. MIB will be updated with
        descriptions for each interface number.
        "
::= {  npSecurityOpenSSLFIPSErrorEntry  1  }

fw-rom-datecode OBJECT-TYPE
        SYNTAX  DisplayString
        ACCESS  read-only
        STATUS  optional
        DESCRIPTION
        "Identifies the base system firmware date code. The date code
        will be encoded in the yyyymmdd format. There may be several
        versions of the base system firmware. The date code associated
        with the version of the base system firmware that is being used
        is reported. There may be other date code objects for other
        specific modules such as fonts, localization modules, etc.;
        these other datecode objects are device specific."
::= { id 5 }

fw-rom-revision OBJECT-TYPE
        SYNTAX  DisplayString
        ACCESS  read-only
        STATUS  optional
        DESCRIPTION
        "This identifies the system code firmware ROM revision code. The
        format for a revision is major_revision.minor_revision. There
        may be other ROM revision code objects for other specific ROMs
        such as font ROMs, localization ROMs, etc; these other ROM
        revision code objects are device specific."
::= { id 6 }

gdPasswords	OBJECT-TYPE
        SYNTAX			OCTET STRING  ( SIZE ( 0 .. 255  ) )
        MAX-ACCESS		read-write
        STATUS			current
        DESCRIPTION
        "This object is used as a 256 byte NVRAM area for JetAdmin.  It
        is completely managed by JetAdmin.  Initially it is initialized
        to all zeros.  A coldboot will re-initialize to all zeros."
::=  {  generalDeviceStatus  13  }

gdStatusBusy	OBJECT-TYPE
        SYNTAX			Integer32  ( 0 .. 255  )
        MAX-ACCESS		read-only
        STATUS			current
        DESCRIPTION
        "This indicates that the peripheral is busy processing
        print/plot data."
::=  {  gdStatusEntry  14  }

gdStatusDisplay	OBJECT-TYPE
        SYNTAX			DisplayString
        MAX-ACCESS		read-only
        STATUS			current
        DESCRIPTION
        "The string diplayed on the peripheral front panel."
::=  {  generalDeviceStatus  3  }

gdStatusDoorOpen	OBJECT-TYPE
        SYNTAX			Integer32  ( 0 .. 255  )
        MAX-ACCESS		read-only
        STATUS			current
        DESCRIPTION
        "This indicates that the peripheral cover or door is open."
::=  {  gdStatusEntry  17  }

gdStatusId	OBJECT-TYPE
        SYNTAX			OCTET STRING  ( SIZE ( 0 .. 1024  ) )
        MAX-ACCESS		read-only
        STATUS			current
        DESCRIPTION
        "A formatted string of NVT ASCII
        charactersdescribing this peripheral."
::=  {  generalDeviceStatus  7  }

gdStatusInitialize	OBJECT-TYPE
        SYNTAX			Integer32
        MAX-ACCESS		read-only
        STATUS			current
        DESCRIPTION
        "This indicates that the peripheral is initializing or
        warming up.
        off (0),
        initializing (1),
        warm-up(2)"
::=  {  gdStatusEntry  16  }

gdStatusJobTimeout	OBJECT-TYPE
        SYNTAX			Integer32
        MAX-ACCESS		read-write
        STATUS			obsolete
        DESCRIPTION
        "This value represents (in seconds) the maximum time of
        inactivity which must elapse before the print server card
        switches from the current network protocol to another when
        a normal end of job is not detected."
::=  {  generalDeviceStatus  10  }

gdStatusLineState	OBJECT-TYPE
        SYNTAX			Integer32  ( 0 .. 255  )
        MAX-ACCESS		read-only
        STATUS			current
        DESCRIPTION
        "This describes the line state of the peripheral.
        When non-zero, the peripheral is off-line.  When
        zero the peripheral is on-line."
::=  {  gdStatusEntry  1  }

gdStatusPaperJam	OBJECT-TYPE
        SYNTAX			Integer32
        MAX-ACCESS		read-only
        STATUS			current
        DESCRIPTION
        "This indicates that the peripheral has a paper jam.
        off (0),
        paper-jam(1)"
::=  {  gdStatusEntry  9  }

gdStatusPaperOut	OBJECT-TYPE
        SYNTAX			Integer32
        MAX-ACCESS		read-only
        STATUS			current
        DESCRIPTION
        "This indicates that the peripheral is out of paper.
        off (0),
        paper-out-or-paper-mount (1),
        manual-paper-feed-needed (2)"
::=  {  gdStatusEntry  8  }

gdStatusPaperOutput	OBJECT-TYPE
        SYNTAX			Integer32
        MAX-ACCESS		read-only
        STATUS			current
        DESCRIPTION
        "This indicates that the peripheral has a paper output problem
        such as the output storage bin being full.
        off (0),
        output-storage-full (1)"
::=  {  gdStatusEntry  19  }

gdStatusPrinting	OBJECT-TYPE
        SYNTAX			Integer32
        MAX-ACCESS		read-only
        STATUS			current
        DESCRIPTION
        "This indicates that the peripheral is printing or otherwise
        marking or moving paper.
        off (0),
        ordinary-page (1),
        test-fonts-config-or-start-page (2)"
::=  {  gdStatusEntry  18  }

gdStatusWait	OBJECT-TYPE
        SYNTAX			Integer32  ( 0 .. 255  )
        MAX-ACCESS		read-only
        STATUS			current
        DESCRIPTION
        "This indicates that the peripheral is waiting for print/plot
        data to process."
::=  {  gdStatusEntry  15  }

getCommunityName	OBJECT-TYPE
        SYNTAX			OCTET STRING  ( SIZE ( 0 .. 255  ) )
        MAX-ACCESS		read-write
        STATUS			current
        DESCRIPTION
        "This object controls access of snmp read requests.  Factory
        default configuration provides authentication of incoming packets
        with community names: internal and public.  This object provides
        access in addition to the factory default settings. If
        set, then authentication will succeed with any of the following
        community names: internal, public, getCommunityName, or
        setCommunityName. This object returns SET or NOT_SET."
::=  {  community  2  }

hrDeviceDescr OBJECT-TYPE
        SYNTAX     DisplayString (SIZE (0..64))
        MAX-ACCESS read-only
        STATUS     current
        DESCRIPTION
        "A textual description of this device, including the
        device's manufacturer and revision, and optionally,
        its serial number."
::= { hrDeviceEntry 3 }

hrDeviceErrors OBJECT-TYPE
        SYNTAX     Counter32
        MAX-ACCESS read-only
        STATUS     current
        DESCRIPTION
        "The number of errors detected on this device.  It
        should be noted that as this object has a SYNTAX of
        Counter32, that it does not have a defined initial
        value.  However, it is recommended that this object be
        initialized to zero, even though management stations
        must not depend on such an initialization."
::= { hrDeviceEntry 6 }

hrDeviceID OBJECT-TYPE
        SYNTAX     ProductID
        MAX-ACCESS read-only
        STATUS     current
        DESCRIPTION
        "The product ID for this device."
::= { hrDeviceEntry 4 }

hrDeviceIndex OBJECT-TYPE
        SYNTAX     Integer32 (1..2147483647)
        MAX-ACCESS read-only
        STATUS     current
        DESCRIPTION
        "A unique value for each device contained by the host.
        The value for each device must remain constant at
        least from one re-initialization of the agent to the
        next re-initialization."
::= { hrDeviceEntry 1 }

hrDeviceStatus OBJECT-TYPE
        SYNTAX     INTEGER {
        unknown(1),
        running(2),
        warning(3),
        testing(4),
        down(5)
        }
        MAX-ACCESS read-only
        STATUS     current
        DESCRIPTION
        "The current operational state of the device described
        by this row of the table.  A value unknown(1)
        indicates that the current state of the device is
        unknown.  running(2) indicates that the device is up
        and running and that no unusual error conditions are
        known.  The warning(3) state indicates that agent has
        been informed of an unusual error condition by the
        operational software (e.g., a disk device driver) but
        that the device is still 'operational'.  An example
        would be a high number of soft errors on a disk.  A
        value of testing(4), indicates that the device is not
        available for use because it is in the testing state.
        The state of down(5) is used only when the agent has
        been informed that the device is not available for any
        use."
::= { hrDeviceEntry 5 }

hrDeviceType OBJECT-TYPE
        SYNTAX     AutonomousType
        MAX-ACCESS read-only
        STATUS     current
        DESCRIPTION
        "An indication of the type of device.
        If this value is
        `hrDeviceProcessor { hrDeviceTypes 3 }' then an entry
        exists in the hrProcessorTable which corresponds to
        this device.
        If this value is
        `hrDeviceNetwork { hrDeviceTypes 4 }', then an entry
        exists in the hrNetworkTable which corresponds to this
        device.
        If this value is
        `hrDevicePrinter { hrDeviceTypes 5 }', then an entry
        exists in the hrPrinterTable which corresponds to this
        device.
        If this value is
        `hrDeviceDiskStorage { hrDeviceTypes 6 }', then an
        entry exists in the hrDiskStorageTable which
        corresponds to this device."
::= { hrDeviceEntry 2 }

hrDiskStorageAccess OBJECT-TYPE
        SYNTAX     INTEGER {
        readWrite(1),
        readOnly(2)
        }
        MAX-ACCESS read-only
        STATUS     current
        DESCRIPTION
        "An indication if this long-term storage device is
        readable and writable or only readable.  This should
        reflect the media type, any write-protect mechanism,
        and any device configuration that affects the entire
        device."
::= { hrDiskStorageEntry 1 }

hrDiskStorageCapacity OBJECT-TYPE
        SYNTAX     KBytes
        UNITS      "KBytes"
        MAX-ACCESS read-only
        STATUS     current
        DESCRIPTION
        "The total size for this long-term storage device. If
        the media is removable and is currently removed, this
        value should be zero."
::= { hrDiskStorageEntry 4 }

hrDiskStorageMedia OBJECT-TYPE
        SYNTAX     INTEGER {
        other(1),
        unknown(2),
        hardDisk(3),
        floppyDisk(4),
        opticalDiskROM(5),
        opticalDiskWORM(6),     -- Write Once Read Many
        opticalDiskRW(7),
        ramDisk(8)
        }
        MAX-ACCESS read-only
        STATUS     current
        DESCRIPTION
        "An indication of the type of media used in this long-
        term storage device."
::= { hrDiskStorageEntry 2 }

hrDiskStorageRemoveble OBJECT-TYPE
        SYNTAX     TruthValue
        MAX-ACCESS read-only
        STATUS     current
        DESCRIPTION
        "Denotes whether or not the disk media may be removed
        from the drive."
::= { hrDiskStorageEntry 3 }

hrMemorySize OBJECT-TYPE
        SYNTAX     KBytes
        UNITS      "KBytes"
        MAX-ACCESS read-only
        STATUS     current
        DESCRIPTION
        "The amount of physical read-write main memory,
        typically RAM, contained by the host."
::= { hrStorage 2 }

hrPrinterDetectedErrorState OBJECT-TYPE
        SYNTAX     OCTET STRING
        MAX-ACCESS read-only
        STATUS     current
        DESCRIPTION
        "This object represents any error conditions detected
        by the printer.  The error conditions are encoded as
        bits in an octet string, with the following
        definitions:
        Condition         Bit #
        lowPaper              0
        noPaper               1
        lowToner              2
        noToner               3
        doorOpen              4
        jammed                5
        offline               6
        serviceRequested      7
        inputTrayMissing      8
        outputTrayMissing     9
        markerSupplyMissing  10
        outputNearFull       11
        outputFull           12
        inputTrayEmpty       13
        overduePreventMaint  14
        Bits are numbered starting with the most significant
        bit of the first byte being bit 0, the least
        significant bit of the first byte being bit 7, the
        most significant bit of the second byte being bit 8,
        and so on.  A one bit encodes that the condition was
        detected, while a zero bit encodes that the condition
        was not detected.
        This object is useful for alerting an operator to
        specific warning or error conditions that may occur,
        especially those requiring human intervention."
::= { hrPrinterEntry 2 }

hrPrinterStatus OBJECT-TYPE
        SYNTAX     INTEGER {
        other(1),
        unknown(2),
        idle(3),
        printing(4),
        warmup(5)
        }
        MAX-ACCESS read-only
        STATUS     current
        DESCRIPTION
        "The current status of this printer device."
::= { hrPrinterEntry 1 }

hrStorageAllocationUnits OBJECT-TYPE
        SYNTAX     Integer32 (1..2147483647)
        UNITS      "Bytes"
        MAX-ACCESS read-only
        STATUS     current
        DESCRIPTION
        "The size, in bytes, of the data objects allocated
        from this pool.  If this entry is monitoring sectors,
        blocks, buffers, or packets, for example, this number
        will commonly be greater than one.  Otherwise this
        number will typically be one."
::= { hrStorageEntry 4 }

hrStorageDescr OBJECT-TYPE
        SYNTAX     DisplayString
        MAX-ACCESS read-only
        STATUS     current
        DESCRIPTION
        "A description of the type and instance of the storage
        described by this entry."
::= { hrStorageEntry 3 }

hrStorageIndex OBJECT-TYPE
        SYNTAX     Integer32 (1..2147483647)
        MAX-ACCESS read-only
        STATUS     current
        DESCRIPTION
        "A unique value for each logical storage area
        contained by the host."
::= { hrStorageEntry 1 }

hrStorageSize OBJECT-TYPE
        SYNTAX     Integer32 (0..2147483647)
        MAX-ACCESS read-write
        STATUS     current
        DESCRIPTION
        "The size of the storage represented by this entry, in
        units of hrStorageAllocationUnits. This object is
        writable to allow remote configuration of the size of
        the storage area in those cases where such an
        operation makes sense and is possible on the
        underlying system. For example, the amount of main
        memory allocated to a buffer pool might be modified or
        the amount of disk space allocated to virtual memory
        might be modified."
::= { hrStorageEntry 5 }

hrStorageType OBJECT-TYPE
        SYNTAX     AutonomousType
        MAX-ACCESS read-only
        STATUS     current
        DESCRIPTION
        "The type of storage represented by this entry."
::= { hrStorageEntry 2 }

hrStorageUsed OBJECT-TYPE
        SYNTAX     Integer32 (0..2147483647)
        MAX-ACCESS read-only
        STATUS     current
        DESCRIPTION
        "The amount of the storage represented by this entry
        that is allocated, in units of
        hrStorageAllocationUnits."
::= { hrStorageEntry 6 }

hrStorageAllocationFailures OBJECT-TYPE
        SYNTAX     Counter32
        MAX-ACCESS read-only
        STATUS     current
        DESCRIPTION
        "The number of requests for storage represented by
        this entry that could not be honored due to not enough
        storage.  It should be noted that as this object has a
        SYNTAX of Counter32, that it does not have a defined
        initial value.  However, it is recommended that this
        object be initialized to zero, even though management
        stations must not depend on such an initialization."
::= { hrStorageEntry 7 }

hrSystemUptime OBJECT-TYPE
        SYNTAX     TimeTicks
        MAX-ACCESS read-only
        STATUS     current
        DESCRIPTION
        "The amount of time since this host was last
        initialized.  Note that this is different from
        sysUpTime in the SNMPv2-MIB [RFC1907] because
        sysUpTime is the uptime of the network management
        portion of the system."
::= { hrSystem 1 }

ifAdminStatus OBJECT-TYPE
        SYNTAX  INTEGER {
        up(1),       -- ready to pass packets
        down(2),
        testing(3)   -- in some test mode
        }
        ACCESS  read-write
        STATUS  mandatory
        DESCRIPTION
        "The desired state of the interface.  The
        testing(3) state indicates that no operational
        packets can be passed."
::= { ifEntry 7 }

ifDescr OBJECT-TYPE
        SYNTAX  DisplayString (SIZE (0..255))
        ACCESS  read-only
        STATUS  mandatory
        DESCRIPTION
        "A textual string containing information about the
        interface.  This string should include the name of
        the manufacturer, the product name and the version
        of the hardware interface."
::= { ifEntry 2 }

ifInDiscards OBJECT-TYPE
        SYNTAX  Counter
        ACCESS  read-only
        STATUS  mandatory
        DESCRIPTION
        "The number of inbound packets which were chosen
        to be discarded even though no errors had been
        detected to prevent their being deliverable to a
        higher-layer protocol.  One possible reason for
        discarding such a packet could be to free up
        buffer space."
::= { ifEntry 13 }

ifInErrors OBJECT-TYPE
        SYNTAX  Counter
        ACCESS  read-only
        STATUS  mandatory
        DESCRIPTION
        "The number of inbound packets that contained
        errors preventing them from being deliverable to a
        higher-layer protocol."
::= { ifEntry 14 }

ifInNUcastPkts OBJECT-TYPE
        SYNTAX  Counter
        ACCESS  read-only
        STATUS  mandatory
        DESCRIPTION
        "The number of non-unicast (i.e., subnetwork-
        broadcast or subnetwork-multicast) packets
        delivered to a higher-layer protocol."
::= { ifEntry 12 }

ifInOctets OBJECT-TYPE
        SYNTAX  Counter
        ACCESS  read-only
        STATUS  mandatory
        DESCRIPTION
        "The total number of octets received on the
        interface, including framing characters."
::= { ifEntry 10 }

ifInUcastPkts OBJECT-TYPE
        SYNTAX  Counter
        ACCESS  read-only
        STATUS  mandatory
        DESCRIPTION
        "The number of subnetwork-unicast packets
        delivered to a higher-layer protocol."
::= { ifEntry 11 }

ifInUnknownProtos OBJECT-TYPE
        SYNTAX  Counter
        ACCESS  read-only
        STATUS  mandatory
        DESCRIPTION
        "The number of packets received via the interface
        which were discarded because of an unknown or
        unsupported protocol."
::= { ifEntry 15 }

ifIndex OBJECT-TYPE
        SYNTAX  INTEGER
        ACCESS  read-only
        STATUS  mandatory
        DESCRIPTION
        "A unique value for each interface.  Its value
        ranges between 1 and the value of ifNumber.  The
        value for each interface must remain constant at
        least from one re-initialization of the entity's
        network management system to the next re-
        initialization."
::= { ifEntry 1 }

ifLastChange OBJECT-TYPE
        SYNTAX  TimeTicks
        ACCESS  read-only
        STATUS  mandatory
        DESCRIPTION
        "The value of sysUpTime at the time the interface
        entered its current operational state.  If the
        current state was entered prior to the last re-
        initialization of the local network management
        subsystem, then this object contains a zero
        value."
::= { ifEntry 9 }

ifMtu OBJECT-TYPE
        SYNTAX  INTEGER
        ACCESS  read-only
        STATUS  mandatory
        DESCRIPTION
        "The size of the largest datagram which can be
        sent/received on the interface, specified in
        octets.  For interfaces that are used for
        transmitting network datagrams, this is the size
        of the largest network datagram that can be sent
        on the interface."
::= { ifEntry 4 }

ifNumber OBJECT-TYPE
        SYNTAX  INTEGER
        ACCESS  read-only
        STATUS  mandatory
        DESCRIPTION
        "The number of network interfaces (regardless of
        their current state) present on this system."
::= { interfaces 1 }

ifOperStatus OBJECT-TYPE
        SYNTAX  INTEGER {
        up(1),       -- ready to pass packets
        down(2),
        testing(3)   -- in some test mode
        }
        ACCESS  read-only
        STATUS  mandatory
        DESCRIPTION
        "The current operational state of the interface.
        The testing(3) state indicates that no operational
        packets can be passed."
::= { ifEntry 8 }

ifOutDiscards OBJECT-TYPE
        SYNTAX  Counter
        ACCESS  read-only
        STATUS  mandatory
        DESCRIPTION
        "The number of outbound packets which were chosen
        to be discarded even though no errors had been
        detected to prevent their being transmitted.  One
        possible reason for discarding such a packet could
        be to free up buffer space."
::= { ifEntry 19 }

ifOutErrors OBJECT-TYPE
        SYNTAX  Counter
        ACCESS  read-only
        STATUS  mandatory
        DESCRIPTION
        "The number of outbound packets that could not be
        transmitted because of errors."
::= { ifEntry 20 }

ifOutNUcastPkts OBJECT-TYPE
        SYNTAX  Counter
        ACCESS  read-only
        STATUS  mandatory
        DESCRIPTION
        "The total number of packets that higher-level
        protocols requested be transmitted to a non-
        unicast (i.e., a subnetwork-broadcast or
        subnetwork-multicast) address, including those
        that were discarded or not sent."
::= { ifEntry 18 }

ifOutOctets OBJECT-TYPE
        SYNTAX  Counter
        ACCESS  read-only
        STATUS  mandatory
        DESCRIPTION
        "The total number of octets transmitted out of the
        interface, including framing characters."
::= { ifEntry 16 }

ifOutQLen OBJECT-TYPE
        SYNTAX  Gauge
        ACCESS  read-only
        STATUS  mandatory
        DESCRIPTION
        "The length of the output packet queue (in
        packets)."
::= { ifEntry 21 }

ifOutUcastPkts OBJECT-TYPE
        SYNTAX  Counter
        ACCESS  read-only
        STATUS  mandatory
        DESCRIPTION
        "The total number of packets that higher-level
        protocols requested be transmitted to a
        subnetwork-unicast address, including those that
        were discarded or not sent."
::= { ifEntry 17 }

ifPhysAddress OBJECT-TYPE
        SYNTAX  PhysAddress
        ACCESS  read-only
        STATUS  mandatory
        DESCRIPTION
        "The interface's address at the protocol layer
        immediately `below' the network layer in the
        protocol stack.  For interfaces which do not have
        such an address (e.g., a serial line), this object
        should contain an octet string of zero length."
::= { ifEntry 6 }

ifSpecific OBJECT-TYPE
        SYNTAX  OBJECT IDENTIFIER
        ACCESS  read-only
        STATUS  mandatory
        DESCRIPTION
        "A reference to MIB definitions specific to the
        particular media being used to realize the
        interface.  For example, if the interface is
        realized by an ethernet, then the value of this
        object refers to a document defining objects
        specific to ethernet.  If this information is not
        present, its value should be set to the OBJECT
        IDENTIFIER { 0 0 }, which is a syntatically valid
        object identifier, and any conformant
        implementation of ASN.1 and BER must be able to
        generate and recognize this value."
::= { ifEntry 22 }

ifSpeed OBJECT-TYPE
        SYNTAX  Gauge
        ACCESS  read-only
        STATUS  mandatory
        DESCRIPTION
        "An estimate of the interface's current bandwidth
        in bits per second.  For interfaces which do not
        vary in bandwidth or for those where no accurate
        estimation can be made, this object should contain
        the nominal bandwidth."
::= { ifEntry 5 }

ifTableLastChange  OBJECT-TYPE
        SYNTAX      TimeTicks
        MAX-ACCESS  read-only
        STATUS      current
        DESCRIPTION
        "The value of sysUpTime at the time of the last creation or
        deletion of an entry in the ifTable.  If the number of
        entries has been unchanged since the last re-initialization
        of the local network management subsystem, then this object
        contains a zero value."
::= { ifMIBObjects 5 }

ifType OBJECT-TYPE
        SYNTAX  INTEGER {
        other(1),          -- none of the following
        regular1822(2),
        hdh1822(3),
        ddn-x25(4),
        rfc877-x25(5),
        ethernet-csmacd(6),
        iso88023-csmacd(7),
        iso88024-tokenBus(8),
        iso88025-tokenRing(9),
        iso88026-man(10),
        starLan(11),
        proteon-10Mbit(12),
        proteon-80Mbit(13),
        hyperchannel(14),
        fddi(15),
        lapb(16),
        sdlc(17),
        ds1(18),           -- T-1
        e1(19),            -- european equiv. of T-1
        basicISDN(20),
        primaryISDN(21),   -- proprietary serial
        propPointToPointSerial(22),
        ppp(23),
        softwareLoopback(24),
        eon(25),            -- CLNP over IP [11]
        ethernet-3Mbit(26),
        nsip(27),           -- XNS over IP
        slip(28),           -- generic SLIP
        ultra(29),          -- ULTRA technologies
        ds3(30),            -- T-3
        sip(31),            -- SMDS
        frame-relay(32)
        }
        ACCESS  read-only
        STATUS  mandatory
        DESCRIPTION
        "The type of interface, distinguished according to
        the physical/link protocol(s) immediately `below'
        the network layer in the protocol stack."
::= { ifEntry 3 }

install-date OBJECT-TYPE
        SYNTAX  DisplayString (SIZE(13))
        ACCESS  read-write
        STATUS  optional
        DESCRIPTION
        "Identifies the date that the device was installed. The format
        of the string is 'YYYYMMDDHHmmZ'. Where:
        YYYY is the year.
        MM is the month (1-12).
        DD is the day (1-31).
        HH is the hour of the day (0-23).
        mm are the minutes (0-59).
        'Z' designates Greenwich Mean Time; if 'Z' not specified,
        value is local time.
        Device POS must specify the conditions for setting this
        object."
::= { status-system 8 }

ipAdEntAddr OBJECT-TYPE
        SYNTAX  IpAddress
        ACCESS  read-only
        STATUS  mandatory
        DESCRIPTION
        "The IP address to which this entry's addressing
        information pertains."
::= { ipAddrEntry 1 }

ipAdEntBcastAddr OBJECT-TYPE
        SYNTAX  INTEGER
        ACCESS  read-only
        STATUS  mandatory
        DESCRIPTION
        "The value of the least-significant bit in the IP
        broadcast address used for sending datagrams on
        the (logical) interface associated with the IP
        address of this entry.  For example, when the
        Internet standard all-ones broadcast address is
        used, the value will be 1.  This value applies to
        both the subnet and network broadcasts addresses
        used by the entity on this (logical) interface."
::= { ipAddrEntry 4 }

ipAdEntIfIndex OBJECT-TYPE
        SYNTAX  INTEGER
        ACCESS  read-only
        STATUS  mandatory
        DESCRIPTION
        "The index value which uniquely identifies the
        interface to which this entry is applicable.  The
        interface identified by a particular value of this
        index is the same interface as identified by the
        same value of ifIndex."
::= { ipAddrEntry 2 }

ipAdEntNetMask OBJECT-TYPE
        SYNTAX  IpAddress
        ACCESS  read-only
        STATUS  mandatory
        DESCRIPTION
        "The subnet mask associated with the IP address of
        this entry.  The value of the mask is an IP
        address with all the network bits set to 1 and all
        the hosts bits set to 0."
::= { ipAddrEntry 3 }

ipDefaultTTL OBJECT-TYPE
        SYNTAX  INTEGER
        ACCESS  read-write
        STATUS  mandatory
        DESCRIPTION
        "The default value inserted into the Time-To-Live
        field of the IP header of datagrams originated at
        this entity, whenever a TTL value is not supplied
        by the transport layer protocol."
::= { ip 2 }

ipForwDatagrams OBJECT-TYPE
        SYNTAX  Counter
        ACCESS  read-only
        STATUS  mandatory
        DESCRIPTION
        "The number of input datagrams for which this
        entity was not their final IP destination, as a
        result of which an attempt was made to find a
        route to forward them to that final destination.
        In entities which do not act as IP Gateways, this
        counter will include only those packets which were
        Source-Routed via this entity, and the Source-
        Route option processing was successful."
::= { ip 6 }

ipForwarding OBJECT-TYPE
        SYNTAX  INTEGER {
        forwarding(1),    -- acting as a gateway
        not-forwarding(2) -- NOT acting as a gateway
        }
        ACCESS  read-write
        STATUS  mandatory
        DESCRIPTION
        "The indication of whether this entity is acting
        as an IP gateway in respect to the forwarding of
        datagrams received by, but not addressed to, this
        entity.  IP gateways forward datagrams.  IP hosts
        do not (except those source-routed via the host).
        Note that for some managed nodes, this object may
        take on only a subset of the values possible.
        Accordingly, it is appropriate for an agent to
        return a `badValue' response if a management
        station attempts to change this object to an
        inappropriate value."
::= { ip 1 }

ipFragCreates OBJECT-TYPE
        SYNTAX  Counter
        ACCESS  read-only
        STATUS  mandatory
        DESCRIPTION
        "The number of IP datagram fragments that have
        been generated as a result of fragmentation at
        this entity."
::= { ip 19 }

ipFragFails OBJECT-TYPE
        SYNTAX  Counter
        ACCESS  read-only
        STATUS  mandatory
        DESCRIPTION
        "The number of IP datagrams that have been
        discarded because they needed to be fragmented at
        this entity but could not be, e.g., because their
        Don't Fragment flag was set."
::= { ip 18 }

ipFragOKs OBJECT-TYPE
        SYNTAX  Counter
        ACCESS  read-only
        STATUS  mandatory
        DESCRIPTION
        "The number of IP datagrams that have been
        successfully fragmented at this entity."
::= { ip 17 }

ipInAddrErrors OBJECT-TYPE
        SYNTAX  Counter
        ACCESS  read-only
        STATUS  mandatory
        DESCRIPTION
        "The number of input datagrams discarded because
        the IP address in their IP header's destination
        field was not a valid address to be received at
        this entity.  This count includes invalid
        addresses (e.g., 0.0.0.0) and addresses of
        unsupported Classes (e.g., Class E).  For entities
        which are not IP Gateways and therefore do not
        forward datagrams, this counter includes datagrams
        discarded because the destination address was not
        a local address."
::= { ip 5 }

ipInDelivers OBJECT-TYPE
        SYNTAX  Counter
        ACCESS  read-only
        STATUS  mandatory
        DESCRIPTION
        "The total number of input datagrams successfully
        delivered to IP user-protocols (including ICMP)."
::= { ip 9 }

ipInDiscards OBJECT-TYPE
        SYNTAX  Counter
        ACCESS  read-only
        STATUS  mandatory
        DESCRIPTION
        "The number of input IP datagrams for which no
        problems were encountered to prevent their
        continued processing, but which were discarded
        (e.g., for lack of buffer space).  Note that this
        counter does not include any datagrams discarded
        while awaiting re-assembly."
::= { ip 8 }

ipInHdrErrors OBJECT-TYPE
        SYNTAX  Counter
        ACCESS  read-only
        STATUS  mandatory
        DESCRIPTION
        "The number of input datagrams discarded due to
        errors in their IP headers, including bad
        checksums, version number mismatch, other format
        errors, time-to-live exceeded, errors discovered
        in processing their IP options, etc."
::= { ip 4 }

ipInReceives OBJECT-TYPE
        SYNTAX  Counter
        ACCESS  read-only
        STATUS  mandatory
        DESCRIPTION
        "The total number of input datagrams received from
        interfaces, including those received in error."
::= { ip 3 }

ipInUnknownProtos OBJECT-TYPE
        SYNTAX  Counter
        ACCESS  read-only
        STATUS  mandatory
        DESCRIPTION
        "The number of locally-addressed datagrams
        received successfully but discarded because of an
        unknown or unsupported protocol."
::= { ip 7 }

ipNetToMediaIfIndex OBJECT-TYPE
        SYNTAX  INTEGER
        ACCESS  read-write
        STATUS  mandatory
        DESCRIPTION
        "The interface on which this entry's equivalence
        is effective.  The interface identified by a
        particular value of this index is the same
        interface as identified by the same value of
        ifIndex."
::= { ipNetToMediaEntry 1 }

ipNetToMediaNetAddress OBJECT-TYPE
        SYNTAX  IpAddress
        ACCESS  read-write
        STATUS  mandatory
        DESCRIPTION
        "The IpAddress corresponding to the media-
        dependent `physical' address."
::= { ipNetToMediaEntry 3 }

ipNetToMediaPhysAddress OBJECT-TYPE
        SYNTAX  PhysAddress
        ACCESS  read-write
        STATUS  mandatory
        DESCRIPTION
        "The media-dependent `physical' address."
::= { ipNetToMediaEntry 2 }

ipNetToMediaType OBJECT-TYPE
        SYNTAX  INTEGER {
        other(1),        -- none of the following
        invalid(2),      -- an invalidated mapping
        dynamic(3),
        static(4)
        }
        ACCESS  read-write
        STATUS  mandatory
        DESCRIPTION
        "The type of mapping.
        Setting this object to the value invalid(2) has
        the effect of invalidating the corresponding entry
        in the ipNetToMediaTable.  That is, it effectively
        dissasociates the interface identified with said
        entry from the mapping identified with said entry.
        It is an implementation-specific matter as to
        whether the agent removes an invalidated entry
        from the table.  Accordingly, management stations
        must be prepared to receive tabular information
        from agents that corresponds to entries not
        currently in use.  Proper interpretation of such
        entries requires examination of the relevant
        ipNetToMediaType object."
::= { ipNetToMediaEntry 4 }

ipOutDiscards OBJECT-TYPE
        SYNTAX  Counter
        ACCESS  read-only
        STATUS  mandatory
        DESCRIPTION
        "The number of output IP datagrams for which no
        problem was encountered to prevent their
        transmission to their destination, but which were
        discarded (e.g., for lack of buffer space).  Note
        that this counter would include datagrams counted
        in ipForwDatagrams if any such packets met this
        (discretionary) discard criterion."
::= { ip 11 }

ipOutNoRoutes OBJECT-TYPE
        SYNTAX  Counter
        ACCESS  read-only
        STATUS  mandatory
        DESCRIPTION
        "The number of IP datagrams discarded because no
        route could be found to transmit them to their
        destination.  Note that this counter includes any
        packets counted in ipForwDatagrams which meet this
        `no-route' criterion.  Note that this includes any
        datagarms which a host cannot route because all of
        its default gateways are down."
::= { ip 12 }

ipOutRequests OBJECT-TYPE
        SYNTAX  Counter
        ACCESS  read-only
        STATUS  mandatory
        DESCRIPTION
        "The total number of IP datagrams which local IP
        user-protocols (including ICMP) supplied to IP in
        requests for transmission.  Note that this counter
        does not include any datagrams counted in
        ipForwDatagrams."
::= { ip 10 }

ipReasmFails OBJECT-TYPE
        SYNTAX  Counter
        ACCESS  read-only
        STATUS  mandatory
        DESCRIPTION
        "The number of failures detected by the IP re-
        assembly algorithm (for whatever reason: timed
        out, errors, etc).  Note that this is not
        necessarily a count of discarded IP fragments
        since some algorithms (notably the algorithm in
        RFC 815) can lose track of the number of fragments
        by combining them as they are received."
::= { ip 16 }

ipReasmOKs OBJECT-TYPE
        SYNTAX  Counter
        ACCESS  read-only
        STATUS  mandatory
        DESCRIPTION
        "The number of IP datagrams successfully re-
        assembled."
::= { ip 15 }

ipReasmReqds OBJECT-TYPE
        SYNTAX  Counter
        ACCESS  read-only
        STATUS  mandatory
        DESCRIPTION
        "The number of IP fragments received which needed
        to be reassembled at this entity."
::= { ip 14 }

ipReasmTimeout OBJECT-TYPE
        SYNTAX  INTEGER
        ACCESS  read-only
        STATUS  mandatory
        DESCRIPTION
        "The maximum number of seconds which received
        fragments are held while they are awaiting
        reassembly at this entity."
::= { ip 13 }

ipRouteDest OBJECT-TYPE
        SYNTAX  IpAddress
        ACCESS  read-write
        STATUS  mandatory
        DESCRIPTION
        "The destination IP address of this route.  An
        entry with a value of 0.0.0.0 is considered a
        default route.  Multiple routes to a single
        destination can appear in the table, but access to
        such multiple entries is dependent on the table-
        access mechanisms defined by the network
        management protocol in use."
::= { ipRouteEntry 1 }

ipRouteIfIndex OBJECT-TYPE
        SYNTAX  INTEGER
        ACCESS  read-write
        STATUS  mandatory
        DESCRIPTION
        "The index value which uniquely identifies the
        local interface through which the next hop of this
        route should be reached.  The interface identified
        by a particular value of this index is the same
        interface as identified by the same value of
        ifIndex."
::= { ipRouteEntry 2 }

ipRouteInfo OBJECT-TYPE
        SYNTAX  OBJECT IDENTIFIER
        ACCESS  read-only
        STATUS  mandatory
        DESCRIPTION
        "A reference to MIB definitions specific to the
        particular routing protocol which is responsible
        for this route, as determined by the value
        specified in the route's ipRouteProto value.  If
        this information is not present, its value should
        be set to the OBJECT IDENTIFIER { 0 0 }, which is
        a syntatically valid object identifier, and any
        conformant implementation of ASN.1 and BER must be
        able to generate and recognize this value."
::= { ipRouteEntry 13 }

ipRouteMask OBJECT-TYPE
        SYNTAX  IpAddress
        ACCESS  read-write
        STATUS  mandatory
        DESCRIPTION
        "Indicate the mask to be logical-ANDed with the
        destination address before being compared to the
        value in the ipRouteDest field.  For those systems
        that do not support arbitrary subnet masks, an
        agent constructs the value of the ipRouteMask by
        determining whether the value of the correspondent
        ipRouteDest field belong to a class-A, B, or C
        network, and then using one of:
        mask           network
        255.0.0.0      class-A
        255.255.0.0    class-B
        255.255.255.0  class-C
        If the value of the ipRouteDest is 0.0.0.0 (a
        default route), then the mask value is also
        0.0.0.0.  It should be noted that all IP routing
        subsystems implicitly use this mechanism."
::= { ipRouteEntry 11 }

ipRouteMetric1 OBJECT-TYPE
        SYNTAX  INTEGER
        ACCESS  read-write
        STATUS  mandatory
        DESCRIPTION
        "The primary routing metric for this route.  The
        semantics of this metric are determined by the
        routing-protocol specified in the route's
        ipRouteProto value.  If this metric is not used,
        its value should be set to -1."
::= { ipRouteEntry 3 }

ipRouteNextHop OBJECT-TYPE
        SYNTAX  IpAddress
        ACCESS  read-write
        STATUS  mandatory
        DESCRIPTION
        "The IP address of the next hop of this route.
        (In the case of a route bound to an interface
        which is realized via a broadcast media, the value
        of this field is the agent's IP address on that
        interface.)"
::= { ipRouteEntry 7 }

ipRouteProto OBJECT-TYPE
        SYNTAX  INTEGER {
        other(1),       -- none of the following
        -- non-protocol information,
        -- e.g., manually configured
        local(2),       -- entries
        -- set via a network
        netmgmt(3),     -- management protocol
        -- obtained via ICMP,
        icmp(4),        -- e.g., Redirect
        -- the remaining values are
        -- all gateway routing
        -- protocols
        egp(5),
        ggp(6),
        hello(7),
        rip(8),
        is-is(9),
        es-is(10),
        ciscoIgrp(11),
        bbnSpfIgp(12),
        ospf(13),
        bgp(14)
        }
        ACCESS  read-only
        STATUS  mandatory
        DESCRIPTION
        "The routing mechanism via which this route was
        learned.  Inclusion of values for gateway routing
        protocols is not intended to imply that hosts
        should support those protocols."
::= { ipRouteEntry 9 }

ipRouteType OBJECT-TYPE
        SYNTAX  INTEGER {
        other(1),        -- none of the following
        invalid(2),      -- an invalidated route
        -- route to directly
        direct(3),       -- connected (sub-)network
        -- route to a non-local
        indirect(4)      -- host/network/sub-network
        }
        ACCESS  read-write
        STATUS  mandatory
        DESCRIPTION
        "The type of route.  Note that the values
        direct(3) and indirect(4) refer to the notion of
        direct and indirect routing in the IP
        architecture.
        Setting this object to the value invalid(2) has
        the effect of invalidating the corresponding entry
        in the ipRouteTable object.  That is, it
        effectively dissasociates the destination
        identified with said entry from the route
        identified with said entry.  It is an
        implementation-specific matter as to whether the
        agent removes an invalidated entry from the table.
        Accordingly, management stations must be prepared
        to receive tabular information from agents that
        corresponds to entries not currently in use.
        Proper interpretation of such entries requires
        examination of the relevant ipRouteType object."
::= { ipRouteEntry 8 }

ipRoutingDiscards OBJECT-TYPE
        SYNTAX  Counter
        ACCESS  read-only
        STATUS  mandatory
        DESCRIPTION
        "The number of routing entries which were chosen
        to be discarded even though they are valid.  One
        possible reason for discarding such an entry could
        be to free-up buffer space for other routing
        entries."
::= { ip 23 }

job-storage-available OBJECT-TYPE
        SYNTAX  INTEGER {
        eFalse(0),
        eTrue(1)
        }
        ACCESS  read-write
        STATUS  optional
        DESCRIPTION
        "This object indicates whether job storage is available on the
        device. The default is eTrue(1) but if storage is not available
        for any reason the return value will be eFalse(0). USE The
        client or driver can query object to see if job storage is
        available."
::= { settings-job 21 }

job-storage-encryption OBJECT-TYPE
        SYNTAX  OCTET STRING
        ACCESS  read-write
        STATUS  optional
        DESCRIPTION
        "This object indicates the kind of encryption supported by
        device. USE The client or driver can query this object to
        determine the kind of encryption supported by this device. In
        case device supports multiple encryption types, it would return
        the comma separated string of all supported encryption types
        e.g. 'aes128,aes256'."
::= { settings-job 22 }

job-storage-mode OBJECT-TYPE
        SYNTAX  OCTET STRING
        ACCESS  read-write
        STATUS  optional
        DESCRIPTION
        "This object indicates what kind of stored job modes this device
        supports. A returned value of none indicates that the device
        does not support job storage. A returned value of save-only
        indicates that the device is configured for save only mode. A
        returned value of print-save indicates that the device supports
        Print and Save mode. In case device supports multiple Job
        Storage modes, it would return the comma separated string with
        all supported values e.g.save-only,print-save. Save-only job
        storage mode indicates that jobs would be stored on device,
        while print-save mode indicates that job would be printed as
        well stored on device. USE The client or driver can query this
        object to see whether the printer has the capability to store
        jobs or to store and print jobs."
::= { settings-job 20 }

job-storage-supported OBJECT-TYPE
        SYNTAX  INTEGER {
        eFalse(0),
        eTrue(1)
        }
        ACCESS  read-write
        STATUS  optional
        DESCRIPTION
        "This object returns eTrue(1) if job storage is supported on
        this device and eFalse(0) if job storage is not supported.
        USE: The client or driver can query this object in
        order to determine whether job storage is supported."
::= { settings-job 18 }

job-storage-type OBJECT-TYPE
        SYNTAX  OCTET STRING
        ACCESS  read-write
        STATUS  optional
        DESCRIPTION
        "This object indicates what kind of stored job types this device
        supports. A returned value of none indicates that the job
        storage is not supported. A returned value of retentive
        indicates that stored jobs are retained across a power cycle. A
        returned value of volatile indicates that stored jobs will be
        lost when a power-cycle occurs. In case device supports
        multiple Job Storage types, it would return the comma separated
        string with all supported values e.g. retentive,volatile USE:
        The client or driver can query this object to determine whether
        the device has the capability to retain stored jobs across a
        power cycle."
::= { settings-job 19 }

max-dpi-quality-pdl-display-tag		OBJECT-TYPE
        SYNTAX     INTEGER {
        cLaserQualityNormalMode(1000),
        cLaserQualityBestMode(1002),
        cLaserQualityDraftMode(1003),
        cLaserQualityMaximumMode(1004),
        cLaserQualityEconoMode(1005),
        cInkQualityDraftMode(3000),
        cInkQualityNormalMode(3001),
        cInkQualityBestMode(3002),
        cInkQualityMaximumMode(3003)
        }
        ACCESS     read-only
        STATUS     optional
        DESCRIPTION "Returns an Enum corresponding to the Description used by the client to provide a display string of quality attributes associated with Max Quality."
::= { max-dpi-quality-pdl 3 }

max-dpi-quality-pdl-hint-tag		OBJECT-TYPE
        SYNTAX     INTEGER {
        cLaserQualityNormalColorHint(2000),
        cLaserQualityNormalMonoHint(2001),
        cLaserQualityBestHint(2002),
        cLaserQualityDraftHint(2003),
        cLaserQualityMaximumHint(2004),
        cLaserQualityEconoHint(2005),
        cInkQualityDraftHint(4000),
        cInkQualityNormalHint(4005),
        cInkQualityBestHint(4010),
        cInkQualityMaximumHint(4015)
        }
        ACCESS     read-only
        STATUS     optional
        DESCRIPTION "Returns an Enum corresponding to the Description used by the client to provide underlying technology behind print quality such as ImageREt."
::= { max-dpi-quality-pdl 2 }

max-dpi-quality-pdl-optimum-resolution		OBJECT-TYPE
        SYNTAX     INTEGER {
        e150(1),
        e300(2),
        e600(3),
        e1200(4)
        }
        ACCESS     read-only
        STATUS     optional
        DESCRIPTION "Indicates the current DPI option selected for the max quality.
        Reference resolution at the bottom of the mib for latest enumeration information."
::= { max-dpi-quality-pdl 1 }

media-names-enabled OBJECT-TYPE
        SYNTAX  OCTET STRING
        ACCESS  read-write
        STATUS  optional
        DESCRIPTION
        "The value of this object controls whish of the MEDIAx-NAME
        objects are supported. Of a bit is set to zero then the attempt
        to get or set the corresponding MEDIAx-NAME objects will return
        <ErrorUnknownObjectIdentifier>"
::= { settings-print-media 3 }

media-size-supported-driver-n-string		OBJECT-TYPE
        SYNTAX	DisplayString
        ACCESS	read-only
        STATUS	mandatory
        DESCRIPTION "Returns the Driver (PJL) string used to specigy a media size,
        for each media size that is supported by a product. PML walk of
        1.4.1.15.1 will return the driver (PJL) name string for each
        media size supported by a product. PML Get of 1.4.1.15.1.X will
        return the driver (PJL) name string of the media size whose PML
        ID maps to X (if it is supported)."
::= { media-sizes 1 }

media1-name OBJECT-TYPE
        SYNTAX  DisplayString (SIZE(1..24))
        ACCESS  read-write
        STATUS  optional
        DESCRIPTION
        "Media 1 name.
        Additional information:
        The symbol set for this string is Roman-8."
::= { media1 1 }

media10-name OBJECT-TYPE
        SYNTAX  DisplayString (SIZE(1..24))
        ACCESS  read-write
        STATUS  optional
        DESCRIPTION
        "Media 10 name.
        Additional information:
        See MEDIA1-NAME."
::= { media10 1 }

media11-name OBJECT-TYPE
        SYNTAX  DisplayString (SIZE(1..24))
        ACCESS  read-write
        STATUS  optional
        DESCRIPTION
        "Media 11 name.
        Additional information:
        See MEDIA1-NAME."
::= { media11 1 }

media12-name OBJECT-TYPE
        SYNTAX  DisplayString (SIZE(1..24))
        ACCESS  read-write
        STATUS  optional
        DESCRIPTION
        "Media 12 name.
        Additional information:
        See MEDIA1-NAME."
::= { media12 1 }

media13-name OBJECT-TYPE
        SYNTAX  DisplayString (SIZE(1..24))
        ACCESS  read-write
        STATUS  optional
        DESCRIPTION
        "Media 13 name.
        Additional information:
        See MEDIA1-NAME."
::= { media13 1 }

media14-name OBJECT-TYPE
        SYNTAX  DisplayString (SIZE(1..24))
        ACCESS  read-write
        STATUS  optional
        DESCRIPTION
        "Media 14 name.
        Additional information:
        See MEDIA1-NAME."
::= { media14 1 }

media15-name OBJECT-TYPE
        SYNTAX  DisplayString (SIZE(1..24))
        ACCESS  read-write
        STATUS  optional
        DESCRIPTION
        "Media 15 name.
        Additional information:
        See MEDIA1-NAME."
::= { media15 1 }

media16-name OBJECT-TYPE
        SYNTAX  DisplayString (SIZE(1..24))
        ACCESS  read-write
        STATUS  optional
        DESCRIPTION
        "Media 16 name.
        Additional information:
        See MEDIA1-NAME."
::= { media16 1 }

media17-name OBJECT-TYPE
        SYNTAX  DisplayString (SIZE(1..24))
        ACCESS  read-write
        STATUS  optional
        DESCRIPTION
        "Media 17 name.
        Additional information:
        See MEDIA1-NAME."
::= { media17 1 }

media18-name OBJECT-TYPE
        SYNTAX  DisplayString (SIZE(1..24))
        ACCESS  read-write
        STATUS  optional
        DESCRIPTION
        "Media 18 name.
        Additional information:
        See MEDIA1-NAME."
::= { media18 1 }

media19-name OBJECT-TYPE
        SYNTAX  DisplayString (SIZE(1..24))
        ACCESS  read-write
        STATUS  optional
        DESCRIPTION
        "Media 19 name.
        Additional information:
        See MEDIA15-NAME."
::= { media19 1 }

media2-name OBJECT-TYPE
        SYNTAX  DisplayString (SIZE(1..24))
        ACCESS  read-write
        STATUS  optional
        DESCRIPTION
        "Media 2 name.
        Additional information:
        The symbol set for this string is Roman-8."
::= { media2 1 }

media20-name OBJECT-TYPE
        SYNTAX  DisplayString (SIZE(1..24))
        ACCESS  read-write
        STATUS  optional
        DESCRIPTION
        "Media 20 name.
        Additional information:
        See MEDIA1-NAME."
::= { media20 1 }

media21-name OBJECT-TYPE
        SYNTAX  DisplayString (SIZE(1..24))
        ACCESS  read-write
        STATUS  optional
        DESCRIPTION
        "Media 21 name.
        Additional information:
        See MEDIA1-NAME."
::= { media21 1 }

media22-name OBJECT-TYPE
        SYNTAX  DisplayString (SIZE(1..24))
        ACCESS  read-write
        STATUS  optional
        DESCRIPTION
        "Media 22 name.
        Additional information:
        See MEDIA1-NAME."
::= { media22 1 }

media23-name OBJECT-TYPE
        SYNTAX  DisplayString (SIZE(1..24))
        ACCESS  read-write
        STATUS  optional
        DESCRIPTION
        "Media 23 name.
        Additional information:
        See MEDIA1-NAME."
::= { media23 1 }

media24-name OBJECT-TYPE
        SYNTAX  DisplayString (SIZE(1..24))
        ACCESS  read-write
        STATUS  optional
        DESCRIPTION
        "Media 24 name.
        Additional information:
        See MEDIA1-NAME."
::= { media24 1 }

media25-name OBJECT-TYPE
        SYNTAX  DisplayString (SIZE(1..24))
        ACCESS  read-write
        STATUS  optional
        DESCRIPTION
        "Media 25 name.
        Additional information:
        See MEDIA1-NAME."
::= { media25 1 }

media26-name OBJECT-TYPE
        SYNTAX  DisplayString (SIZE(1..24))
        ACCESS  read-write
        STATUS  optional
        DESCRIPTION
        "Media 26 name.
        Additional information:
        See MEDIA1-NAME."
::= { media26 1 }

media27-name OBJECT-TYPE
        SYNTAX  DisplayString (SIZE(1..24))
        ACCESS  read-write
        STATUS  optional
        DESCRIPTION
        "Media 27 name.
        Additional information:
        See MEDIA1-NAME."
::= { media27 1 }

media28-name OBJECT-TYPE
        SYNTAX  DisplayString (SIZE(1..24))
        ACCESS  read-write
        STATUS  optional
        DESCRIPTION
        "Media 28 name.
        Additional information:
        See MEDIA1-NAME."
::= { media28 1 }

media29-name OBJECT-TYPE
        SYNTAX  DisplayString (SIZE(1..24))
        ACCESS  read-write
        STATUS  optional
        DESCRIPTION
        "Media 29 name.
        Additional information:
        See MEDIA1-NAME."
::= { media29 1 }

media3-name OBJECT-TYPE
        SYNTAX  DisplayString (SIZE(1..24))
        ACCESS  read-write
        STATUS  optional
        DESCRIPTION
        "Media 3 name.
        Additional information:
        See MEDIA1-NAME."
::= { media3 1 }

media30-name OBJECT-TYPE
        SYNTAX  DisplayString (SIZE(1..24))
        ACCESS  read-write
        STATUS  optional
        DESCRIPTION
        "Media 30 name.
        Additional information:
        See MEDIA1-NAME."
::= { media30 1 }

media31-name OBJECT-TYPE
        SYNTAX  DisplayString (SIZE(1..24))
        ACCESS  read-write
        STATUS  optional
        DESCRIPTION
        "Media 31 name.
        Additional information:
        See MEDIA1-NAME."
::= { media31 1 }

media32-name OBJECT-TYPE
        SYNTAX  DisplayString (SIZE(1..24))
        ACCESS  read-write
        STATUS  optional
        DESCRIPTION
        "Media 32 name.
        Additional information:
        See MEDIA1-NAME."
::= { media32 1 }

media33-name OBJECT-TYPE
        SYNTAX  DisplayString (SIZE(1..24))
        ACCESS  read-write
        STATUS  optional
        DESCRIPTION
        "Media 33 name.
        Additional information:
        See MEDIA1-NAME."
::= { media33 1 }

media34-name OBJECT-TYPE
        SYNTAX  DisplayString (SIZE(1..24))
        ACCESS  read-write
        STATUS  optional
        DESCRIPTION
        "Media 34 name.
        Additional information:
        See MEDIA1-NAME."
::= { media34 1 }

media4-name OBJECT-TYPE
        SYNTAX  DisplayString (SIZE(1..24))
        ACCESS  read-write
        STATUS  optional
        DESCRIPTION
        "Media 4 name.
        Additional information:
        See MEDIA1-NAME."
::= { media4 1 }

media5-name OBJECT-TYPE
        SYNTAX  DisplayString (SIZE(1..24))
        ACCESS  read-write
        STATUS  optional
        DESCRIPTION
        "Media 5 name.
        Additional information:
        See MEDIA1-NAME."
::= { media5 1 }

media6-name OBJECT-TYPE
        SYNTAX  DisplayString (SIZE(1..24))
        ACCESS  read-write
        STATUS  optional
        DESCRIPTION
        "Media 6 name.
        Additional information:
        See MEDIA1-NAME."
::= { media6 1 }

media7-name OBJECT-TYPE
        SYNTAX  DisplayString (SIZE(1..24))
        ACCESS  read-write
        STATUS  optional
        DESCRIPTION
        "Media 7 name.
        Additional information:
        See MEDIA1-NAME."
::= { media7 1 }

media8-name OBJECT-TYPE
        SYNTAX  DisplayString (SIZE(1..24))
        ACCESS  read-write
        STATUS  optional
        DESCRIPTION
        "Media 8 name.
        Additional information:
        See MEDIA1-NAME."
::= { media8 1 }

media9-name OBJECT-TYPE
        SYNTAX  DisplayString (SIZE(1..24))
        ACCESS  read-write
        STATUS  optional
        DESCRIPTION
        "Media 9 name.
        Additional information:
        See MEDIA1-NAME."
::= { media9 1 }

model-derivative	OBJECT-TYPE
        SYNTAX		INTEGER
        ACCESS		read-only
        STATUS		optional
        DESCRIPTION
        "Identifies the device model derivative to distinguish among
        devices with identical MODEL-NAME and identical or unknown
        MODEL-NUMBER values. The device POS must specify the values
        returned by this object and their meanings."
::= { id 16 }

model-name OBJECT-TYPE
        SYNTAX  DisplayString (SIZE(1..32))
        ACCESS  read-only
        STATUS  optional
        DESCRIPTION
        "Identifies the device model name (e.g. ''DeskJet 1200C''). The
        string is as specific as possible. Capitalization and spacing
        should match family naming conventions. Products should note in
        POS if the model name on the HP corporate price list changes
        but the device reports the previous device name. If the model
        name changes based on the installed options, the POS should
        indicate if only the base model name is returned, or if the
        device senses the installed options and returns the correct
        model name. If possible, encode the model name in a symbol set
        (like Roman-8) that matches the ASCII character set and limit
        the characters used to ASCII characters."
::= { id 2 }

model-number OBJECT-TYPE
        SYNTAX  DisplayString
        ACCESS  read-only
        STATUS  optional
        DESCRIPTION
        "Identifies the device model number as listed in the HP
        corporate price list (e.g. C2121A for DeskJet 500C). The string
        is as specific as possible. Products should note in POS if the
        model number on the CPL changes but the device reports the
        previous model number. If the model number changes based on the
        installed options, the POS should indicate if only the base
        model number is returned, or if the device senses the installed
        options and returns the correct model number. If possible,
        encode the model number in a symbol set (like Roman-8) that
        matches the ASCII character set and limit the characters used
        to ASCII characters."
::= { id 1 }

not-ready-tray-empty OBJECT-TYPE
        SYNTAX  OCTET STRING
        ACCESS  read-only
        STATUS  optional
        DESCRIPTION
        "Indicates which trays contain no media causing the device to be
        not ready. Some devices may treat tray missing as a tray empty
        condition.
        Additional information:
        The input trays designated by the bits of
        this collection include the standard input tray(s) plus the
        additional tray(s) attached to the printer."
::= { status-intray 2 }

npCfgAccessListAddrMask			OBJECT-TYPE
        SYNTAX		IpAddress
        MAX-ACCESS	read-write
        STATUS		current
        DESCRIPTION "Address mask used to help determine whether or not a given
        IP address is allowed access to the print server.  An IP address
        is allowed access if (Addr & AddrMask) == (IP & AddrMask).
        A set of this object may only be done if npCfgAccessListAddress
        preceeds it in the same varbind packet."
::=  {  npCfgAccessListEntry  3  }

npCfgAccessListAddress		OBJECT-TYPE
        SYNTAX		IpAddress
        MAX-ACCESS	read-write
        STATUS		current
        DESCRIPTION "The Access List Address contains the list of hosts or network
        of hosts that are allowed to connect to the print server over ip.
        When setting this object npCfgAccessListAddrMask should also
        be set in the same varbind packet. NpCfgAccessListAddress
        should always preceed npCfgAccessListAddrMask in the set packet.
        If npCfgAccessListAddrMask is not set, the default value of
        255.255.255.255 will be assigned to npCfgAccessListAddrMask
        for that particular npCfgAccessListAddress entry. Duplicate host
        addresses are possible and, once set, it is not possible to change
        any particular row other than to clear the Access List Table.
        To clear the Access List Table set npCfgAccessListAddress to 0.0.0.0.
        This table has a maximum of 10 rows."
::=  {  npCfgAccessListEntry  2  }

npCfgAccessListIndex		OBJECT-TYPE
        SYNTAX		Integer32  ( 0 .. 9  )
        MAX-ACCESS	read-only
        STATUS		current
        DESCRIPTION "Index to the configuration access list table."
::=  {  npCfgAccessListEntry  1  }

npCfgAccessListNum		OBJECT-TYPE
        SYNTAX		Integer32
        MAX-ACCESS	read-only
        STATUS		current
        DESCRIPTION "The number of access list entries."
::=  {  npCfg  8  }

npCfgAccessState		OBJECT-TYPE
        SYNTAX		INTEGER  {
        allowed ( 1 ) ,
        not-allowed ( 2 )
        }
        MAX-ACCESS	read-only
        STATUS		current
        DESCRIPTION "An indication of whether or not the requesting host
        is allowed to connect to the card as dictated by the
        access list."
::=  {  npCfg  7  }

npCfgBonjourDomainName	OBJECT-TYPE
        SYNTAX			OCTET STRING  ( SIZE ( 0 .. 255  ) )
        MAX-ACCESS		read-only
        STATUS			current
        DESCRIPTION
        "The name used as the 'target name' in the DNS SRV records by
        Multicast Domain Name System (Bonjour)."
::=  {  npCfg  46  }

npCfgBonjourHighestPriorityService	OBJECT-TYPE
        SYNTAX			INTEGER  { p9100-Printing ( 1 ) , ipp-Printing ( 2 ) , lPD-Printing-RAW ( 3 ) , lPD-Printing-TEXT ( 4 ) , lPD-Printing-AUTO ( 5 ) , lPD-Printing-BINPS ( 6 ) , lPD-Printing-Queue5 ( 7 ) , lPD-Printing-Queue6 ( 8 ) , lPD-Printing-Queue7 ( 9 ) , lPD-Printing-Queue8 ( 10 ) , lPD-Printing-Queue9 ( 11 ) , lPD-Printing-Queue10 ( 12 ) , ipps-Printing ( 16 ) }
        MAX-ACCESS		read-write
        STATUS			current
        DESCRIPTION
        "This object specifies the highest priority service advertised by Bonjour.
        When this object is change, all services will be re-advertised with
        the changed priority."
::=  {  npCfg  45  }

npCfgBonjourServiceName	OBJECT-TYPE
        SYNTAX			OCTET STRING  ( SIZE ( 0 .. 63  ) )
        MAX-ACCESS		read-write
        STATUS			current
        DESCRIPTION
        "The name by which all the Jetdirect services will be advertised by
        Multicast Domain Name System (Bonjour). Must set a non empty string"
::=  {  npCfg  44  }

npCfgDNSNameServerId	OBJECT-TYPE
        SYNTAX			IpAddress
        MAX-ACCESS		read-write
        STATUS			current
        DESCRIPTION
        "IP address of Primary DNS name-server."
::=  {  npCfg  21  }

npCfgDNSNameServerIdSecondary	OBJECT-TYPE
        SYNTAX			IpAddress
        MAX-ACCESS		read-write
        STATUS			current
        DESCRIPTION
        "IP address of Secondary DNS name-server."
::=  {  npCfg  47  }

npCfgDefaultGateway	OBJECT-TYPE
        SYNTAX			IpAddress
        MAX-ACCESS		read-write
        STATUS			current
        DESCRIPTION
        "This variable contains the IP address of the default router for this
        card."
::=  {  npCfg  13  }

npCfgDomainName	OBJECT-TYPE
        SYNTAX			OCTET STRING  ( SIZE ( 0 .. 255  ) )
        MAX-ACCESS		read-write
        STATUS			current
        DESCRIPTION
        "The print server domain name."
::=  {  npCfg  16  }

npCfgHpDAPAgentManualServerAddr		OBJECT-TYPE
        SYNTAX			InetAddress
        MAX-ACCESS		read-write
        STATUS			current
        DESCRIPTION
        "Zero when Empty"
::=  {  npCfg  99  }

npCfgIPConfigPrecedence	OBJECT-TYPE
        SYNTAX			OCTET STRING
        MAX-ACCESS		read-write
        STATUS			current
        DESCRIPTION
        "Allows to set uniform rules for parameter overwrite by
        different configuration methods.
        0 - Manual
        1 - TFTP
        2 - DHCPv4/Bootp
        3 - DHCPv6     - only if ipv6 is supported
        3/4 - Default  - 4 if ipv6 is supported otherwise 3
        The set string should be 0:1:2:3:4 (or 0:1:2:3 when ipv6 is not supported)
        or any colon separated combination of the 5 (or 4) integral values. The
        string should contain all integral values atleast and atmost once."
::=  {  npCfg  59  }

npCfgIPP	OBJECT-TYPE
        SYNTAX			Integer32
        MAX-ACCESS		read-write
        STATUS			current
        DESCRIPTION
        "Below are the different values accepted by this OID.
        0 - Disable IPP and IPP-S
        1 - Enable IPP and IPP-S
        2 - Enable IPP-S only
        3 - Enable IPP only
        "
::=  {  npCfg  18  }

npCfgIPv6ConfigState	OBJECT-TYPE
        SYNTAX			INTEGER  { ipv6-going-down ( 0 ) , ipv6-is-up ( 1 ) }
        MAX-ACCESS		read-only
        STATUS			current
        DESCRIPTION
        "IPv6 stack status event; IPv6 enabled/disabled."
::=  {  npCfg  50  }

npCfgIPv6DNSAddr1	OBJECT-TYPE
        SYNTAX			InetAddress
        MAX-ACCESS		read-write
        STATUS			current
        DESCRIPTION
        "IPv6 DNS Address, priority 1."
::=  {  npCfg  56  }

npCfgIPv6DNSAddr2	OBJECT-TYPE
        SYNTAX			InetAddress
        MAX-ACCESS		read-write
        STATUS			current
        DESCRIPTION
        "IPv6 DNS Address, priority 2."
::=  {  npCfg  57  }

npCfgIPv6DomainName	OBJECT-TYPE
        SYNTAX			InetAddress
        MAX-ACCESS		read-write
        STATUS			current
        DESCRIPTION
        "IPv6 Domain Name."
::=  {  npCfg  49  }

npCfgLinkType	OBJECT-TYPE
        SYNTAX			INTEGER  { autoNegotiate ( 1 ) , full10T ( 2 ) , half10T ( 3 ) , full100T ( 4 ) , half100T ( 5 ) , auto100T ( 6 ) , full1000T ( 7 ) }
        MAX-ACCESS		read-write
        STATUS			current
        DESCRIPTION
        "Network link speed and communication mode."
::=  {  npCfg  35  }

npCfgLogServer	OBJECT-TYPE
        SYNTAX			IpAddress
        MAX-ACCESS		read-write
        STATUS			current
        DESCRIPTION
        "The IP address of the Syslog Server. If set via BOOTP (Tag: 7 field,
        lg=<ipaddress> ) then SNMP set will fail. If not set via BOOTP then SNMP set
        will succeed. Value saved across warm boot power cycles. BOOTP will always
        overwrite SNMP set values."
::=  {  npCfg  5  }

npCfgPasswd1	OBJECT-TYPE
        SYNTAX			DisplayString
        MAX-ACCESS		read-write
        STATUS			current
        DESCRIPTION
        "Password for root or administrator. Get request returns
        either 'SET' or 'NOT_SET'."
::=  {  npCfg  29  }

npCfgSTAWirelessMode 		OBJECT-TYPE
        SYNTAX			INTEGER  { b/g-Mode ( 0 ) , b/g/n-Mode ( 1 ) }
        MAX-ACCESS		read-write
        STATUS			current
        DESCRIPTION
        "Different standardized 802.11 wireless modes.
        The following values are defined:
        0 -  b/g/n-mode (Default)
        1 -  n-mode only
        Note: Guard Interval, AMSDU, Block Acknowledgement, and AMPDU are applicable in 802.11 n modes only.
        "
::=  {  npCfg  72  }

npCfgSiaddr	OBJECT-TYPE
        SYNTAX			IpAddress
        MAX-ACCESS		read-only
        STATUS			current
        DESCRIPTION
        "The IP address of the TFTP server from the BOOTP reply
        siaddr field."
::=  {  npCfg  3  }

npCfgSnmpDefaultReadCmnty	OBJECT-TYPE
        SYNTAX			Integer32  ( 0 .. 1  )
        MAX-ACCESS		read-write
        STATUS			current
        DESCRIPTION
        "Controls Default Read Community Name access.
        (0) = Disabled, i.e., default get community names FAIL to access target.
        (1) = Enabled,  i.e., default get community names SUCCEED to access target."
::=  {  npCfg  40  }

npCfgSource	OBJECT-TYPE
        SYNTAX			INTEGER  { manual-one ( 1 ) , bootp-two ( 2 ) , manual-three ( 3 ) , bootp-four ( 4 ) , dhcp ( 5 ) , not-configured ( 6 ) , default-config ( 7 ) , rarp ( 8 ) , read-only ( 9 ) , auto-ip ( 10 ) }
        MAX-ACCESS		read-write
        STATUS			current
        DESCRIPTION
        "This object indicates how the device obtained its IP configuration."
::=  {  npCfg  1  }

npCfgSubnetMask	OBJECT-TYPE
        SYNTAX			IpAddress
        MAX-ACCESS		read-write
        STATUS			current
        DESCRIPTION
        "The subnet mask associated with the IP address of this card."
::=  {  npCfg  12  }

npCfgSysLogPort			OBJECT-TYPE
        SYNTAX		INTEGER  ( 1 .. 65535  )
        MAX-ACCESS	read-write
        STATUS		current
        DESCRIPTION "Sys Log Server Port.Default set to port number 514"
::=  {  npCfg  98  }

npCfgSysLogProtocol		OBJECT-TYPE
        SYNTAX		INTEGER  { tcp ( 6 ) , udp ( 17 ) }
        MAX-ACCESS	read-write
        STATUS		current
        DESCRIPTION "Protocol  used by SysLog server for communication.
        Default set to UDP"
::=  {  npCfg  97  }

npCfgWINSNameServerIdPri	OBJECT-TYPE
        SYNTAX			IpAddress
        MAX-ACCESS		read-write
        STATUS			current
        DESCRIPTION
        "Primary name server for NetBIOS over TCP/IP."
::=  {  npCfg  22  }

npCfgWINSNameServerIdSec	OBJECT-TYPE
        SYNTAX			IpAddress
        MAX-ACCESS		read-write
        STATUS			current
        DESCRIPTION
        "Secondary name server for NetBIOS over TCP/IP."
::=  {  npCfg  23  }

npCfgWiFiDirectChannelNumber		OBJECT-TYPE
        SYNTAX			INTEGER  ( 1 .. 13 )
        MAX-ACCESS		read-write
        STATUS			current
        DESCRIPTION
        "The WiFi channel number used for Wireless/Wi-Fi Direct.
        Region               Allowed Channels
        -------------------                  ----------------
        US & Worldwide Safe   1 - 11
        Rest of the world          1 - 13
        If wireless station is enabled, this setting is ignored and the
        channel used is determined by the AP to which the device is
        associated to.
        Default channel is 6.
        "
::=  {  npCfg  85  }

npCfgWiFiDirectConnectionSecurity  OBJECT-TYPE
        SYNTAX          INTEGER  { automatic ( 0 ) , manual ( 1 ) , advanced ( 2 ) }
        MAX-ACCESS      read-write
        STATUS          optional
        DESCRIPTION
        "This is used to select the Wi-Fi Direct connection security method
        which differentiates how the connection is done between a mobile
        client and the printer. The following values are defined:
        Automatic  ( 0 )
        Manual     ( 1 )
        Advanced   ( 2 )
        Automatic - Printer will accept all Wi-Fi Direct initiated
        connections without requiring the user to push a button on the
        printer. The user may have to enter a PIN, provided by the printer,
        if the mobile device requests PIN method.
        Manual - Wi-Fi Direct clients require printer interaction to
        connect. The user has to push a button on the printer or enter a
        PIN into the mobile device to connect depending on the method
        requested by mobile device.
        Advanced  - This mode disables Wi-Fi Direct, switches to Wireless
        Direct and allows configuration of advanced settings.
        "
::=  {  npCfg  88 }

npCfgWiFiDirectSSIDPrefix OBJECT-TYPE
        SYNTAX			OCTET STRING ( SIZE ( 1 .. 13  ) )
        MAX-ACCESS		read-only
        STATUS			current
        DESCRIPTION
        "
        The prefix of the network name (SSID) used for Wireless/Wi-Fi
        Direct. The value is 'HP-Print-XY-' where XY is the last two hex
        characters from the wireless MAC address. On products supporting
        Wi-Fi Direct, the value is 'DIRECT-XY-HP '. The prefix is read-only.
        The value of this object is prefixed to the value of
        npCfgWiFiDirectSSIDSuffix to form the complete SSID.
        "
::=  {  npCfg  86  }

npCfgWiFiDirectSSIDSuffix OBJECT-TYPE
        SYNTAX			OCTET STRING ( SIZE ( 1 .. 19  ) )
        MAX-ACCESS		read-write
        STATUS			current
        DESCRIPTION
        "
        The modifiable suffix of the network name (SSID) used for
        Wireless/Wi-Fi Direct. The default is '<sub brand> <hp model>',
        but it can be different depending on printer family.
        The value of this object is concatenated to the value of
        npCfgWiFiDirectSSIDPrefix to form the complete SSID.
        "
::=  {  npCfg  87  }

npCfgYiaddr	OBJECT-TYPE
        SYNTAX			IpAddress
        MAX-ACCESS		read-write
        STATUS			current
        DESCRIPTION
        "The IP address assigned to the card from the BOOTP reply
        yiaddr field."
::=  {  npCfg  2  }

npCtl9100	OBJECT-TYPE
        SYNTAX			Integer32  ( 0 .. 1  )
        MAX-ACCESS		read-write
        STATUS			current
        DESCRIPTION
        "Configure TCP port 9100 printing.
        (0) = port 9100 printing disabled
        (1) = port 9100 printing enabled"
::=  {  npCtl  24  }

npCtlAirFax	OBJECT-TYPE
        SYNTAX		INTEGER { disable (0) , enable (1) }
        MAX-ACCESS	read-write
        STATUS		optional
        DESCRIPTION
        "Used to Enable/Disable the AirFax service.
        Disable = 0
        Enable (Default) = 1"
::= { npCtl 80 }

npCtlAirPrintStatus		OBJECT-TYPE
        SYNTAX			INTEGER  { disable ( 0 ) , enable ( 1 ) }
        MAX-ACCESS		read-write
        STATUS			current
        DESCRIPTION
        " Use to Enabled/Disabled AirPrint functionality.
        Disable				= 0
        Enable(Default)		= 1
        "
::=  {  npCtl  68 }

npCtlAirScan      OBJECT-TYPE
        SYNTAX      INTEGER
        MAX-ACCESS  read-write
        STATUS      optional
        DESCRIPTION
        "Used to Enable/Disable the AirScan and Secure AirScan service.
        The value for this OID is a bit map with the following assignment
        Bit 0 - AirScan
        Bit 1 - Secure AirScan
        This leads to the following values
        Value     Secure-AirScan        AirScan
        ------------------------------------------
        0         Disabled            Disabled
        1         Disabled            Enabled
        2         Enabled             Disabled
        3         Enabled             Enabled
        "
::= { npCtl 79 }

npCtlBonjour	OBJECT-TYPE
        SYNTAX			Integer32  ( 0 .. 1  )
        MAX-ACCESS		read-write
        STATUS			current
        DESCRIPTION
        "Configure Multicast Domain Name Service.
        (0) = Bonjour disabled
        (1) = Bonjour enabled"
::=  {  npCtl  29  }

npCtlDeviceMode		OBJECT-TYPE
        SYNTAX			INTEGER  { wiredStationMode ( 1 ) , wirelessStationMode ( 2 ) , accessPointMode (3) }
        MAX-ACCESS		read-only
        STATUS			current
        DESCRIPTION
        " Use to check the current state of the device.
        WiredStationMode			= 1
        WirelessStationMode			= 2
        AccessPointMode				= 3
        "
::=  {  npCtl  67 }

npCtlDot11nSTAAMPDUAggregation		OBJECT-TYPE
        SYNTAX			INTEGER  { disable ( 0 ) , enable ( 1 ) }
        MAX-ACCESS		read-write
        STATUS			current
        DESCRIPTION
        "802.11n can send multiple frames per single access to the medium by combining frames together into one larger frame.
        There are two forms of frame aggregation:
        Aggregated Mac Service Data Unit (A-MSDU) and Aggregated Mac Protocol Data Unit (A-MPDU).
        A-MSDU increases the maximum frame transmission size from 2,304 bytes to almost 8k bytes (7935 to be exact)
        while A-MPDU allows up to 64k bytes. A-	MSDU creates the larger frame by combining smaller frames with
        the same physical source and destination end points and traffic class (i.e. QoS) into one large frame with a common MAC header.
        Disable				= 0
        Enable(Default)		= 1
        "
::=  {  npCtl  54 }

npCtlDot11nSTAAMSDUAggregation		OBJECT-TYPE
        SYNTAX			INTEGER  { disable ( 0 ) , enable ( 1 ) }
        MAX-ACCESS		read-write
        STATUS			current
        DESCRIPTION
        "802.11n can send multiple frames per single access to the medium by combining frames together into one larger frame.
        There are two forms of frame aggregation:
        Aggregated Mac Service Data Unit (A-MSDU) and Aggregated Mac Protocol Data Unit (A-MPDU).
        A-MSDU increases the maximum frame transmission size from 2,304 bytes to almost 8k bytes (7935 to be exact)
        while A-MPDU allows up to 64k bytes. A-	MSDU creates the larger frame by combining smaller frames with
        the same physical source and destination end points and traffic class (i.e. QoS) into one large frame with a common MAC header.
        Disable				= 0
        Enable(Default)		= 1
        "
::=  {  npCtl  52 }

npCtlDot11nSTABlockACKs		OBJECT-TYPE
        SYNTAX			INTEGER  { disable ( 0 ) , enable ( 1 )}
        MAX-ACCESS		read-write
        STATUS			current
        DESCRIPTION
        "This mechanism allows each of the aggregated data frames to be individually acknowledged or
        retransmitted if affected by an error. Block acknowledgement compiles all the acknowledgements
        of the individual constituent frames produced by MPDU aggregation into a single frame returned
        by the recipient to the sender. This allows a compact and rapid mechanism to implement selective
        retransmission of only those constituent frames that are not acknowledged.
        Disable				= 0
        Enable(Default)		= 1
        "
::=  {  npCtl  53 }

npCtlDot11nSTAGuardInterval 		OBJECT-TYPE
        SYNTAX			INTEGER  { auto ( 0 ) , short ( 1 ) , long ( 2 ) }
        MAX-ACCESS		read-write
        STATUS			current
        DESCRIPTION
        "The guard interval is the space between symbols (characters) being transmitted.
        The guard interval is there to eliminate intersymbol interference, which is referred to as ISI.
        ISI happens when echoes or reflections from one symbol interfere with another. Adding time between
        symbol transmissions allows these echoes and 	reflections to settle in before the next symbol is transmitted.
        Short Guard Interval increases the data rate by roughly 10-11%.
        The following values are defined:
        0 - Auto (default)
        1 - Short
        2 - Long
        "
::=  {  npCtl  51  }

npCtlFpDot11WirelessState	OBJECT-TYPE
        SYNTAX			INTEGER  { disable ( 0 ) , enable ( 1 )}
        MAX-ACCESS		read-write
        STATUS			current
        DESCRIPTION
        "Use for enabling and disabling Wireless Radio.
        The following values are defined:
        Disable		= 0
        Enable		= 1
        Default		= 1(Enabled)"
::=  {  npCtl  47 }

npCtlGCPrint      OBJECT-TYPE
        SYNTAX            INTEGER { disable (0) , enable (1),  remove (2)  }
        MAX-ACCESS     read-write
        STATUS             optional
        DESCRIPTION    "Used to Enable/Disable/Remove(Hide) the GC Print service.
        Disable = 0
        Enable (Default) = 1
        Remove = 2
        If disable is specified and the device is registered for Google
        Cloud Services, then the device will be unregistered.
        When remove is specified to an unregistered device, the
        UI aspects of the feature are hidden from end user, so that the
        user will not be able to see the Google cloud Print Service feature.
        When remove is specified to a registered device, the device will
        disable the feature and remove all user interfaces."
::= { npCtl 81 }

npCtlHpDAPAgentAnnounceState		OBJECT-TYPE
        SYNTAX			INTEGER  { disable ( 0 ) , enable ( 1 ) }
        MAX-ACCESS		read-write
        STATUS			current
        DESCRIPTION
        "
        Disable(Default)			= 0
        Enable						= 1
        "
::=  {  npCtl  65 }

npCtlHpDAPAgentRequireTrustedAuth		OBJECT-TYPE
        SYNTAX			INTEGER  { disable ( 0 ) , enable ( 1 ) }
        MAX-ACCESS		read-write
        STATUS			current
        DESCRIPTION
        "
        Disable(Default)			= 0
        Enable						= 1
        "
::=  {  npCtl  66 }

npCtlLLMNR		OBJECT-TYPE
        SYNTAX			INTEGER  { disable ( 0 ) , enable ( 1 ) }
        MAX-ACCESS		read-write
        STATUS			current
        DESCRIPTION
        "Link-Local Multicast Name Resolution( LLMNR ) enable/disable."
::=  {  npCtl  38  }

npCtlLPD	OBJECT-TYPE
        SYNTAX			Integer32  ( 0 .. 1  )
        MAX-ACCESS		read-write
        STATUS			current
        DESCRIPTION
        "Configure Line Printer Daemon Protocol (LPD) service.
        (0) = LPD disabled
        (1) = LPD enabled"
::=  {  npCtl  22  }

npCtlNetworkConnectionMode	OBJECT-TYPE
        SYNTAX			INTEGER  { auto-cable-detect ( 1 ) , disable-radio ( 2 ) , disable-wired ( 3 ) }
        MAX-ACCESS		read-write
        STATUS			current
        DESCRIPTION
        "This object controls the selection of the active network
        interface used for communication. This is applicable to
        products supporting dual wired and wireless network interfaces"
::=  {  npCtl  32  }

npCtlProtocolSet	OBJECT-TYPE
        SYNTAX			Integer32
        MAX-ACCESS		read-write
        STATUS			current
        DESCRIPTION
        "This is a 4 byte integer value.  The least significant bytes
        represent the protocols on the card.  A value of '1' indicates
        a protocol that is enabled.  A value of '0' indicates a protocol that is disabled.
        The 32-bit protocol enable 'structure' is defined as:
        bits 31-28:  Number of I/O channels/protocols present (NUM_CHAN)
        bits 27-24:  Number of I/O channels which may operate concurrently (NUM_OP_CHAN)
        bits 23-16:  unused, reserved
        bits 15-1:   Individual I/O channel/protocol enable bits,
        0 == disable, 1 == enable
        MIO_IOCHAN_NOVELL   bit   1
        MIO_IOCHAN_LLC      bit   2
        MIO_IOCHAN_TCP      bit   3
        MIO_IOCHAN_ATALK    bit   4
        MIO_IOCHAN_IPV6	    bit   5
        bit  0: When NUM_OP_CHAN == 1, auto-protocol select enable bit,
        0 == disable, 1 == enable  (APS_ON)"
::=  {  npCtl  9  }

npCtlRebootMode        OBJECT-TYPE
        SYNTAX                 INTEGER { normal (0) , recovery (1)}
        MAX-ACCESS             read-write
        STATUS                 optional
        DESCRIPTION            "Used to set a reboot mode on the device.
        normal = 0 (default)
        recovery = 1 (firmware with minimal features, once
        in this mode, device will check a web
        URL for firmware upgrades)
        Setting this OID will force the device to reboot in
        a specified mode. The reboot itself may take upwards
        of 30 seconds (will differ for different devices)
        Note: This was needed by WJA for the newer Sirius
        on Linux class of devices."
::= { npCtl  83 }

npCtlSLP	OBJECT-TYPE
        SYNTAX			Integer32  ( 0 .. 1  )
        MAX-ACCESS		read-write
        STATUS			current
        DESCRIPTION
        "Configure Service Location Protocol (SLP) service.
        (0) = SLP disabled
        (1) = SLP enabled"
::=  {  npCtl  21  }

npCtlSnmpV3InitAccount	OBJECT-TYPE
        SYNTAX			INTEGER  { destroy ( 0 ) , blockInitEncrypt ( 4 ) }
        MAX-ACCESS		read-write
        STATUS			current
        DESCRIPTION
        "Used to create initial SNMPv3 account.  The following rules apply:
        0 = clear init account, only if previously 0.
        4 = Block init account, only cold reset will clear or use Web User interface.
        Setting this object to blocked (4) will block an initial account
        creation until a cold reset."
::=  {  npCtl  28  }

npCtlSnmpVersionAccess	OBJECT-TYPE
        SYNTAX			INTEGER  { snmpV1RW-snmpV3RW ( 1 ) , snmpV1RO-snmpV3RW ( 2 ) , snmpV1NoAccess-snmpV3RW ( 3 ) , snmpV1RW-snmpV3NoAccess ( 4 ) ,snmpV1RO-snmpV3NoAccess ( 5 ) }
        MAX-ACCESS		read-write
        STATUS			current
        DESCRIPTION
        "Manages an SNMP version's read and write access to the MIB."
::=  {  npCtl  27  }

npCtlSysLog	OBJECT-TYPE
        SYNTAX			Integer32  ( 0 .. 1  )
        MAX-ACCESS		read-write
        STATUS			current
        DESCRIPTION
        "Configure Syslog service.
        (0) = Syslog service disabled
        (1) = Syslog service enabled
        Enabled by default."
::=  {  npCtl  26  }

npCtlWPAD		OBJECT-TYPE
        SYNTAX			INTEGER  { disable ( 0 ) , automatic-Web-Proxy ( 1 ) , manual-url ( 2 ) , manual-proxy-settings ( 3 ) }
        MAX-ACCESS		read-write
        STATUS			current
        DESCRIPTION
        " Used to Disable and Enable Web-Proxy Auto Discovery."
::=  {  npCtl  39  }

npCtlWSDiscovery	OBJECT-TYPE
        SYNTAX			INTEGER  { disable ( 0 ) , enable ( 1 ) }
        MAX-ACCESS		read-write
        STATUS			current
        DESCRIPTION
        "Web Services Discovery enable/disable."
::=  {  npCtl  36  }

npCtlWSPrint		OBJECT-TYPE
        SYNTAX			INTEGER  { disable ( 0 ) , enable ( 1 ) }
        MAX-ACCESS		read-write
        STATUS			current
        DESCRIPTION
        "Web Services Print enable/disable."
::=  {  npCtl  37  }

npCtlWiFiDirectHidePassphrase  OBJECT-TYPE
        SYNTAX   INTEGER  { show ( 0 ) , hide ( 1 ) }
        MAX-ACCESS  read-write
        STATUS   optional
        DESCRIPTION
        "This controls display of the Wireless passphrase on configuration
        reports/pages or on the control panel.
        Show = 0
        Hide = 1
        This object also controls whether or not the passphrase is included in the NFC record.
        Hide (1) only takes effect when npCfgWiFiDirectConnectionSecurity is set to Advanced
        "
::=  {  npCtl  58 }

npCtlWiFiDirectHideSsid  OBJECT-TYPE
        SYNTAX   INTEGER  { show ( 0 ) , hide ( 1 ) }
        MAX-ACCESS  read-write
        STATUS   optional
        DESCRIPTION
        "This controls display of the network name (SSID) on configuration
        reports/pages or on the control panel.
        Show = 0
        Hide = 1
        Hide (1) only takes effect when npCfgWifiDirectConnectionSecurity is set to Advanced
        "
::=  {  npCtl  59 }

npCtlWiFiDirectSSIDBroadcast OBJECT-TYPE
        SYNTAX   INTEGER  { not-allowed ( 0 ) , allowed ( 1 ) }
        MAX-ACCESS  read-write
        STATUS   current
        DESCRIPTION
        "This is used to allow or hide broadcasting of the SSID (Network name).
        Allowed(Default) = 1
        Not Allowed      = 0
        Not Allowed (0) only takes effect when npCfgWiFiDirectConnectionSecurity is set to Advanced.
        "
::=  {  npCtl  57 }

npCtlWiFiDirectState OBJECT-TYPE
        SYNTAX  INTEGER  { disabled ( 0 ), enabled ( 1 ) }
        MAX-ACCESS read-write
        STATUS       current
        DESCRIPTION
        "Configure 802.11 Wireless/Wi-Fi Direct  functionality
        0 = Wireless/Wi-Fi Direct is disabled
        1 = Wireless/Wi-Fi Direct is enabled
        "
::=  {  npCtl  74 }

npCtlWirelessSTAState  OBJECT-TYPE
        SYNTAX      INTEGER  { disabled ( 0 ), enabled ( 1 ) }
        MAX-ACCESS  read-write
        STATUS      current
        DESCRIPTION
        "Configure 802.11 wireless station (STA) functionality
        0 = Wireless station is disabled
        1 = Wireless station is enabled
        "
::=  {  npCtl  73 }

npDhcpFQDNBehavior	OBJECT-TYPE
        SYNTAX			INTEGER  { present-JD-Behavior ( 0 ) , rfc4702-compliant-Behavior ( 1 ) }
        MAX-ACCESS		read-write
        STATUS			current
        DESCRIPTION
        "This object defines the FQDN behavior in Jetdirect. Set this to
        ( 0 ) - Present Jetdirect Behavior
        ( 1 ) - RFC 4702 compliant behavior"
::=  {  npDhcp  4  }

npIpxSapInfo	OBJECT-TYPE
        SYNTAX			OCTET STRING
        MAX-ACCESS		read-only
        STATUS			current
        DESCRIPTION
        "This is a 50 byte array that contains the following
        information.
        2 bytes:  bindery object type (always 030c in hi-lo order)
        12 bytes:  Mac address of card (ASCII)
        2 bytes:  frame type
        also high bit (8000) is set if card is not configured
        2 bytes : unit type (hex 81 for NetJet card)
        32 bytes: node name (ASCII) which is:
        print server name for Queue Server mode
        printer name for RPTR mode"
::=  {  npIpx  6  }

npNpiPaeClass	OBJECT-TYPE
        SYNTAX			INTEGER  { printer ( 1 ) , plotter ( 2 ) , xStation ( 3 ) }
        MAX-ACCESS		read-only
        STATUS			current
        DESCRIPTION
        "The class assigned to the peripheral onto which
        this card is plugged."
::=  {  npNpiPeripheralAttributeEntry  2  }

npNpiPaeIdentification	OBJECT-TYPE
        SYNTAX			INTEGER  { laserjet-IIISI ( 1 ) , laserjet-4SI ( 5 ) }
        MAX-ACCESS		read-only
        STATUS			current
        DESCRIPTION
        "The Identification number of the peripheral.  These values are
        defined in the MIO spec.  DesignJet, PaintJet XL300, and
        DesignJet/600 peripherals will identify themselves as
        LaserJet-IIIsi."
::=  {  npNpiPeripheralAttributeEntry  3  }

npPortNumPorts	OBJECT-TYPE
        SYNTAX			Integer32  ( 0 .. 255  )
        MAX-ACCESS		read-only
        STATUS			current
        DESCRIPTION
        "The number of peripheral interfaces supported by this device."
::=  {  npPort  1  }

npSecurityDot11DynamicEncryption	OBJECT-TYPE
        SYNTAX			INTEGER  { none ( 0 ) , basic ( 1 ) , wpa ( 2 ) , wpa2 ( 3 ) , auto ( 4 ) }
        MAX-ACCESS		read-write
        STATUS			current
        DESCRIPTION
        "WPA mode.
        (0x00) = NONE
        (0x01) = BASIC
        (0x02) = WPA
        (0x03) = WPA2
        (0x04) = AUTO"
::=  {  npSecurity  42  }

npSecurityDot11EapAuthServerId    OBJECT-TYPE
        SYNTAX			   OCTET STRING  ( SIZE ( 0 .. 64  ) )
        MAX-ACCESS		   read-write
        STATUS			   current
        DESCRIPTION
        "Server ID relates to the Common Name that is returned in the subject of the Authentication
        Server Certificate and determines how print server should validate the authentication server.
        Few examples:
        1) Server id is blank: If the Authentication Server’s certificate is trusted, accept all Common Names returned
        in the Subject field of the Authentication Server certificate
        2) Server id is configured and “Require Exact Match” is not checked:  If the Authentication server’s certificate
        is trusted, accept all Common Names returned in the Subject field of the Authentication Server certificate that
        have the configured server id as a rightmost subset.
        3) Server id is configured and “Require Exact Match” is enabled: If the Authentication Server’s certificate is
        trusted, accept all Common Names with the exact name
        Note:
        1) This object is used for wireless station configuration on products supporting simultaneous
        Ethernet LAN and wireless station operation. On products supporting wireless via an accessory,
        this object will be available only when the accessory is connected.
        "
::=  {  npSecurity  64  }

npSecurityDot11EapEncryptionStrength    OBJECT-TYPE
        SYNTAX				INTEGER  { low ( 1 ) , medium ( 2 ) , high ( 3 ) }
        MAX-ACCESS			read-write
        STATUS				current
        DESCRIPTION
        "Encryption strength determines the minimum strength of the SSL tunnel by determining what ciphers are advertised by the
        print server in the TLS Client Hello packet. Low, Medium, High encryption strengths corresponds to
        various ciphers and key sizes.
        If FIPS is enabled, default encryption strength set is HIGH.
        Note:
        1) This object is used for wireless station configuration on products supporting simultaneous
        Ethernet LAN and wireless station operation. On products supporting wireless via an accessory,
        this object will be available only when the accessory is connected.
        "
::=  {  npSecurity  67  }

npSecurityDot11EapExactMatchServerId    OBJECT-TYPE
        SYNTAX				TruthValue
        MAX-ACCESS			read-write
        STATUS				current
        DESCRIPTION
        "This OID allows us to configure the “Require Exact Match” feature which indicates how common name from a
        successfully authenticated server is considered.
        Few examples:
        1) Server id is blank: If the Authentication Server’s certificate is trusted, accept all Common Names returned
        in the Subject field of the Authentication Server certificate
        2) Server id is configured and “Require Exact Match” is not checked:  If the Authentication server’s certificate
        is trusted, accept all Common Names returned in the Subject field of the Authentication Server certificate that
        have the configured server id as a rightmost subset.
        3) Server id is configured and “Require Exact Match” is enabled: If the Authentication Server’s certificate is
        trusted, accept all Common Names with the exact name
        Note:
        1) This object is used for wireless station configuration on products supporting simultaneous
        Ethernet LAN and wireless station operation. On products supporting wireless via an accessory,
        this object will be available only when the accessory is connected.
        "
::=  {  npSecurity  65  }

npSecurityDot11EapReAuthenticate        OBJECT-TYPE
        SYNTAX				TruthValue
        MAX-ACCESS			read-only
        STATUS				current
        DESCRIPTION
        "The re-authentication control for this port.
        If set to TRUE, the print server attempts to re-authenticate the Supplicant using the configured values.
        Setting to FALSE has no effect. This OID always returns FALSE when it is read.
        Note:
        1) This object is used for wireless station configuration on products supporting simultaneous
        Ethernet LAN and wireless station operation. On products supporting wireless via an accessory,
        this object will be available only when the accessory is connected.
        "
::=  {  npSecurity  68  }

npSecurityDot11EapServerAuthProtocols   OBJECT-TYPE
        SYNTAX				INTEGER  { eap-md5 ( 1 ) , eap-tls ( 2 ) , leap ( 4 ) , peap ( 8 ) , ttls ( 16 ) }
        MAX-ACCESS			read-write
        STATUS				current
        DESCRIPTION
        "HP print servers support secured network access via Extensible Authentication Protocol (EAP)
        on an IEEE 802.1X network. The IEEE 802.1X standard provides a port-based authentication protocol
        where a network port allows or blocks use, depending on client authentication results.
        When using an 802.1X connection, the print server supports EAP with an authentication server,
        such as a remote authentication dial-in user service (RADIUS, RFC 2138) server.
        Brief description of few currently supported EAP/802.1X methods:
        1) LEAP (lightweight EAP) is a proprietary Cisco Systems protocol that uses passwords for
        mutual authentication. It is used to authenticate access by a wireless client, typically a Cisco
        Aironet base station.
        2) PEAP (Protected EAP) is a mutual authentication protocol that uses digital certificates
        for network server authentication and passwords for client authentication. For additional
        security, the authentication exchanges are encapsulated within transport layer security (TLS).
        Dynamic encryption keys are used for secure communications.
        3) EAP-TLS (RFC 2716) is a mutual authentication protocol based on X.509v3–compliant digital
        certificates for authentication of both the client and the network authentication server.
        Dynamic encryption keys are used for secure communications.
        The following bitwise values are defined for this OID:
        None(0),
        EAP-MD5(1),
        EAP-TLS(2),
        LEAP(4),
        PEAP(8),
        TTLS(16)
        Note:
        1) This object is used for wireless station configuration on products supporting simultaneous
        Ethernet LAN and wireless station operation. On products supporting wireless via an accessory,
        this object will be available only when the accessory is connected.
        2) Not all of the above protocols might be supported on the printer. Use the OID
        npSecurityServicesSupported (1.3.6.1.4.1.11.2.4.3.20.27.0) to determine the supported protocols.
        "
::=  {  npSecurity  53  }

npSecurityDot11EapUsername    OBJECT-TYPE
        SYNTAX			OCTET STRING  ( SIZE ( 0 .. 130  ) )
        MAX-ACCESS		read-write
        STATUS			current
        DESCRIPTION
        "Username required by EAP/802.1x Authentication methods.
        Note:
        1) This object is used for wireless station configuration on products supporting simultaneous
        Ethernet LAN and wireless station operation. On products supporting wireless via an accessory,
        this object will be available only when the accessory is connected.
        "
::=  {  npSecurity  54  }

npSecurityDot11EncryptedWEPKey	OBJECT-TYPE
        SYNTAX			OCTET STRING  ( SIZE ( 0 .. 13  ) )
        MAX-ACCESS		write-only
        STATUS			current
        DESCRIPTION
        "The encrypted WEP Key value.  Use
        the npSecurityDot11PublicKey to encrypt this value.
        Setting this object will cause the card to reconfigure."
::=  {  npSecurityDot11EncryptedWEPKeyEntry  2  }

npSecurityDot11EncryptedWPAConfigPSKPassPhrase	OBJECT-TYPE
        SYNTAX			OCTET STRING  ( SIZE ( 0 | 8 .. 63  ) )
        MAX-ACCESS		write-only
        STATUS			current
        DESCRIPTION
        "The encrypted WPA Config PSK PassPhrase.  Use the
        npSecurityPublicKey to encrypt this value"
::=  {  npSecurity  36  }

npSecurityDot11Encryption	OBJECT-TYPE
        SYNTAX			Integer32
        MAX-ACCESS		read-write
        STATUS			current
        DESCRIPTION
        "802.11 encryption method currently enabled.
        The following values are defined:
        NONE       (0x00)
        SSN/WEP    (0x01)
        TKIP       (0x02)
        AES        (0x03)
        AUTO       (0x04)
        Reserved  (5 - 31)
        It is advised not to use dot11PrivacyInvoked OID anymore, instead use npSecurityDot11Encryption.
        Since Jetdirect updates the same variable when the set happens through any of the two OIDs and
        npSecurityDot11Encryption is more versatile, it is recommended to use this OID.
        "
::=  {  npSecurity  28  }

npSecurityDot11LinkAuthentication	OBJECT-TYPE
        SYNTAX			INTEGER  { open ( 1 ) , shared-key ( 2 ) , leap ( 128 ) , auto ( 143 ) }
        MAX-ACCESS		read-write
        STATUS			current
        DESCRIPTION
        "DOT11 Link Authentication modes.
        (1) = OPEN
        (2) = SHARED-KEY
        (128) = LEAP
        (143) = AUTO
        We can set the Link Authentication using the object dot11AuthenticationAlgorithmsEnable ( OID: 1.2.840.10036.1.2.1.3.x )
        Since the dot11AuthenticationAlgorithsmEnable object does not supports setting of AUTO option, we provide this object.
        Through this OID you can set to any one of the above options.
        Whereas using the dot11AuthenticationAlgorithmsEnable object we can set either OPEN OR SHARED mode only."
::=  {  npSecurity  43 }

npSecurityDot11MulticastCipher	OBJECT-TYPE
        SYNTAX			Integer32
        MAX-ACCESS		read-write
        STATUS			current
        DESCRIPTION
        "BITWISE indication of the multicast cipher method currently enabled.
        At minimum, one bit must be set.
        The following bits are defined:
        WEP       (0)
        WPA       (1)
        Reserved  (2 - 31)"
::=  {  npSecurity  29  }

npSecurityDot11SSID	OBJECT-TYPE
        SYNTAX			OCTET STRING  ( SIZE ( 0 .. 32  ) )
        MAX-ACCESS		read-only
        STATUS			current
        DESCRIPTION
        "A discovered SSID value."
::=  {  npSecurityDot11SSIDEntry  2  }

npSecurityDot11SSIDTableNumEntries	OBJECT-TYPE
        SYNTAX			Integer32
        MAX-ACCESS		read-only
        STATUS			current
        DESCRIPTION
        "Displays the number of discovered SSIDs in
        the SSID Table."
::=  {  npSecurity  10  }

npSecurityDot11ServicesSupported	OBJECT-TYPE
        SYNTAX				Integer32
        MAX-ACCESS			read-only
        STATUS				current
        DESCRIPTION
        "BITWISE indication of the 802.11 security services this device supports.
        The following bits are defined:
        MD5                               (0)
        TLS                               (1)
        TTLS                              (2)
        LEAP                              (3)
        PEAP                              (4)
        Reserved                        (5 - 15)
        WEP                               (16)
        WPA                               (17)
        AES                               (18)
        WPA2                              (19)
        AUTO_FOR_WEP_SUPPORTED            (20)
        AUTO_FOR_WPA_SUPPORTED            (21)
        AUTO_FOR_ENCRYPTION_SUPPORTED     (22)
        Reserved  (23 - 31)
        Note:
        1) This object is used for wireless station configuration on products supporting simultaneous
        Ethernet LAN and wireless station operation. On products supporting wireless via an accessory,
        this object will be available only when the accessory is connected.
        "
::=  {  npSecurity  66  }

npSecurityDot11SignalStrength	OBJECT-TYPE
        SYNTAX			INTEGER  { level-1-TBD ( 1 ) , level-2-TBD ( 2 ) , level-3-TBD ( 3 ) , level-4-TBD ( 4 ) , level-5-TBD ( 5 ) }
        MAX-ACCESS		read-only
        STATUS			current
        DESCRIPTION
        "A weighted average over time of the signal strength
        between the access point and the print server in infrastructure
        mode. Not applicable when in ad hoc mode."
::=  {  npSecurity  8  }

npSecurityDot1xAuthServerId	OBJECT-TYPE
        SYNTAX			OCTET STRING  ( SIZE ( 0 .. 64  ) )
        MAX-ACCESS		read-write
        STATUS			current
        DESCRIPTION
        "Server ID relates to the Common Name that is returned in the subject of the Authentication
        Server Certificate and determines how print server should validate the authentication server.
        Server ID can be configured with a partial string (right-most characters) unless the 'Require Exact Match' feature
        is enabled.
        Few examples:
        1) Server id is blank: If the Authentication Server's certificate is trusted, accept all Common Names
        returned in the Subject field of the Authentication Server certificate
        2) Server id is configured and 'Require Exact Match' is not enabled:  If the Authentication server's certificate
        is trusted, accept all Common Names returned in the Subject field of the Authentication Server certificate
        that have the configured server id as a rightmost subset.
        3) Server id is configured and 'Require Exact Match' is enabled: If the Authentication Server's certificate
        is trusted, accept all Common Names with the exact name"
::=  {  npSecurity  3  }

npSecurityDot1xEncryptionStrength	OBJECT-TYPE
        SYNTAX			INTEGER  { low ( 1 ) , medium ( 2 ) , high ( 3 ) }
        MAX-ACCESS		read-write
        STATUS			current
        DESCRIPTION
        "Encryption strength determines the minimum strength of the SSL tunnel by determining what ciphers are advertised by the
        print server in the TLS Client Hello packet. Low, Medium, High encryption strengths corresponds to
        various ciphers and key sizes.
        If FIPS is enabled, default encryption strength set is HIGH.
        "
::=  {  npSecurity  20  }

npSecurityDot1xExactMatchServerId	OBJECT-TYPE
        SYNTAX			TruthValue
        MAX-ACCESS		read-write
        STATUS			current
        DESCRIPTION
        "This OID allows us to configure the 'Require Exact Match' feature which indicates
        how common name from a successfully authenticated server is considered.
        Few examples:
        1) Server id is blank: If the Authentication Server's certificate is trusted, accept all Common Names
        returned in the Subject field of the Authentication Server certificate
        2) Server id is configured and 'Require Exact Match' is not enabled:  If the Authentication server's certificate
        is trusted, accept all Common Names returned in the Subject field of the Authentication Server certificate
        that have the configured server id as a rightmost subset.
        3) Server id is configured and 'Require Exact Match' is enabled: If the Authentication Server's certificate
        is trusted, accept all Common Names with the exact name
        "
::=  {  npSecurity  19  }

npSecurityDot1xFailSafe		OBJECT-TYPE
        SYNTAX                      INTEGER  { enable ( 1 ) , disable ( 0 ) }
        MAX-ACCESS                  read-write
        STATUS                      current
        DESCRIPTION
        "After configuring 802.1x on the printer and switching it over to a secured network, if authentication is
        successful printer retains connectivity and if it fails it loses connectivity.
        In case of authentication failure, it does not acquire connectivity even when switched over to an unsecured network.
        802.1x failsafe is a feature which allows printer to retain connectivity in a unsecured network even if authentication fails.
        Setting this OID to 1 enables this feature and setting to 0 disables this feature.
        Connect anyway (802.1x Fail-Safe)           ( 1 )
        Block network  (secure failure)             ( 0 )
        "
::=  { npSecurity  57 }

npSecurityDot1xReAuthenticate	OBJECT-TYPE
        SYNTAX			TruthValue
        MAX-ACCESS		read-only
        STATUS			current
        DESCRIPTION
        "The re-authentication control for this port.
        If set to TRUE, the print server attempts to re-authenticate the Supplicant using the configured values.
        Setting to FALSE has no effect. This OID always returns FALSE when it is read.
        "
::=  {  npSecurity  52  }

npSecurityDot1xServerAuthProtocols    OBJECT-TYPE
        SYNTAX			INTEGER  { eap-md5 ( 1 ) , eap-tls ( 2 ) , leap ( 4 ) , peap ( 8 ) , ttls ( 16 ) }
        MAX-ACCESS		read-write
        STATUS			current
        DESCRIPTION
        "HP print servers support secured network access via Extensible Authentication Protocol (EAP)
        on an IEEE 802.1X network. The IEEE 802.1X standard provides a port-based authentication protocol
        where a network port allows or blocks use, depending on client authentication results.
        When using an 802.1X connection, the print server supports EAP with an authentication server,
        such as a remote authentication dial-in user service (RADIUS, RFC 2138) server.
        Brief description of few currently supported EAP/802.1X methods:
        1) LEAP (lightweight EAP) is a proprietary Cisco Systems protocol that uses passwords for
        mutual authentication. It is used to authenticate access by a wireless client, typically a Cisco
        Aironet base station.
        2) PEAP (Protected EAP) is a mutual authentication protocol that uses digital certificates
        for network server authentication and passwords for client authentication. For additional
        security, the authentication exchanges are encapsulated within transport layer security (TLS).
        Dynamic encryption keys are used for secure communications.
        3) EAP-TLS (RFC 2716) is a mutual authentication protocol based on X.509v3-compliant digital
        certificates for authentication of both the client and the network authentication server.
        Dynamic encryption keys are used for secure communications.
        The following bitwise values are defined for this OID:
        None(0),
        EAP-MD5(1),
        EAP-TLS(2),
        LEAP(4),
        PEAP(8),
        TTLS(16)
        Note:
        1) Not all of the above protocols might be supported on the printer. Use the OID
        npSecurityServicesSupported (1.3.6.1.4.1.11.2.4.3.20.27.0) to determine the supported protocols.
        "
::=  {  npSecurity  1  }

npSecurityDot1xUsername	OBJECT-TYPE
        SYNTAX			OCTET STRING  ( SIZE ( 0 .. 130  ) )
        MAX-ACCESS		read-write
        STATUS			current
        DESCRIPTION
        "Username required by EAP/802.1x Authentication methods.
        "
::=  {  npSecurity  2  }

npSecurityEncryptedDot11EapPassword     OBJECT-TYPE
        SYNTAX				OCTET STRING  ( SIZE ( 0 .. 130  ) )
        MAX-ACCESS			write-only
        STATUS				current
        DESCRIPTION
        "Password required by EAP/802.1x Authentication methods
        Use the npSecurityPublicKey (1.3.6.1.4.1.11.2.4.3.20.4.0) to encrypt this value
        using RSA public key encryption before performing snmpset.
        This is OID is logically write-only and a SnmpGet returns SET or NOT_SET.
        Note:
        1) This object is used for wireless station configuration on products supporting simultaneous
        Ethernet LAN and wireless station operation. On products supporting wireless via an accessory,
        this object will be available only when the accessory is connected.
        "
::=  {  npSecurity  56  }

npSecurityEncryptedDot1xPassword	OBJECT-TYPE
        SYNTAX			OCTET STRING  ( SIZE ( 0 .. 130  ) )
        MAX-ACCESS		read-write
        STATUS			current
        DESCRIPTION
        "Password required by EAP/802.1x Authentication methods
        Use the npSecurityPublicKey (1.3.6.1.4.1.11.2.4.3.20.4.0) to encrypt this value using
        RSA public key encryption before performing snmpset.
        This is OID is logically write-only and a SnmpGet returns SET or NOT_SET.
        "
::=  {  npSecurity  6  }

npSecurityPublicKey	OBJECT-TYPE
        SYNTAX			OCTET STRING  ( SIZE ( 0 .. 64  ) )
        MAX-ACCESS		read-only
        STATUS			current
        DESCRIPTION
        "The public key of a public/private key pair to be
        used by applications to set encrypted values."
::=  {  npSecurity  4  }

npSecuritySSLProtocol		OBJECT-TYPE
        SYNTAX                      INTEGER
        MAX-ACCESS                  read-write
        STATUS                      current
        DESCRIPTION
        "
        Different SSL Protocols can be selected with the following bitwise values:
        SSL 3.0 (1)
        TLS 1.0 (2)
        TLS 1.1 (4)
        TLS 1.2 (8)
        "
::=  { npSecurity  58 }

npSecurityServicesSupported	OBJECT-TYPE
        SYNTAX			Integer32
        MAX-ACCESS		read-only
        STATUS			current
        DESCRIPTION
        "BITWISE indication of the 802.11 security services this device supports.
        The following bits are defined:
        MD5       						(0)
        TLS       						(1)
        TTLS      						(2)
        LEAP      						(3)
        PEAP      						(4)
        Reserved  						(5 - 15)
        WEP       						(16)
        WPA       						(17)
        AES       						(18)
        WPA2      						(19)
        AUTO_FOR_WEP_SUPPORTED      	(20)
        AUTO_FOR_WPA_SUPPORTED      	(21)
        AUTO_FOR_ENCRYPTION_SUPPORTED   (22)
        Reserved  (23 - 31)"
::=  {  npSecurity  27  }

npSecuritySnmpV3AuthAlgorithm	OBJECT-TYPE
        SYNTAX			INTEGER  { md5 ( 2 ), sha-1 ( 3 ) }
        MAX-ACCESS		read-write
        STATUS			current
        DESCRIPTION
        "Indicates the Authentication Algorithm used.
        It can have the value MD5 or SHA-1.
        This key will have a default value set to MD5.
        The following values are defined:
        MD5    2 (Default)
        SHA-1  3
        "
::=  {  npSecurity  44 }

npSecuritySnmpV3AuthKeyPassPhrase		OBJECT-TYPE
        SYNTAX		OCTET STRING  ( SIZE ( 256 ) )
        MAX-ACCESS	write-only
        STATUS		current
        DESCRIPTION
        "The encrypted SNMPv3 Authentication passphrase or key .
        Use the npSecurityPublicKey to encrypt this value.
        When setting this object, all three user account objects (npSecuritySnmpV3EncryptedUserName,
        npSecuritySnmpV3AuthKeyPassPhrase, and npSecuritySnmpV3PrivKeyPassPhrase) should also be set in
        the same multi-varbind request.
        Implementations may accept the objects in separate SNMP requests, or they may return a inconsistentValue (12)
        failure to indicate that other objects are required.
        If setting the objects individually is allowed, the User Account will not be installed until after all three
        objects have been set.
        The other OID's related to SNMPv3 authentication are
        npSecuritySnmpV3AuthAlgorithm and npSecuritySnmpV3PassPhrase, please ensure that they are set appropriately.
        This OID can only be SET if the inital SNMP V3 account is not created
        (i.e. the value of npCtlSnmpV3InitAccount is 0)
        The values of npSecuritySnmpV3AuthAlgorithm and npSecuritySnmpV3PassPhrase must be set appropriately
        before setting the value of this OID.
        To enhance security, some implementations enforce min length and complexity check for the Auth Passphrase.
        The printer would return a 'badValue(v1)' or 'wrongLength(v2)' error  when the passphrase is of a shorter length
        and would return 'badValue(v1)' or 'wrongValue(v2)' error when the password does not meet the complexity criteria.
        Query npSecuritySnmpV3AuthPassMinLen(1.3.6.1.4.1.11.2.4.3.20.72.0) to get min length required.
        Query npSecuritySnmpV3PasswordComplexity(1.3.6.1.4.1.11.2.4.3.20.73.0) to know if complexity check is enabled.
        "
::=  {  npSecurity  14  }

npSecuritySnmpV3AuthPassMinLen	OBJECT-TYPE
        SYNTAX			Integer32 (8 .. 255)
        MAX-ACCESS		read-write
        STATUS			current
        DESCRIPTION
        "Used to configure the minimum length of the Authentication passphrase to be used
        while creating the SNMPv3 init account using EWS or SNMPv1/v2.
        "
::= { npSecurity  72  }

npSecuritySnmpV3EncryptedUserName	OBJECT-TYPE
        SYNTAX			OCTET STRING  ( SIZE ( 256 ) )
        MAX-ACCESS		write-only
        STATUS			current
        DESCRIPTION
        "The encrypted SNMPv3 User Name.
        Use the npSecurityPublicKey to encrypt this value.
        The new SNMPv3 User Account will be installed after the
        npSecuritySnmpV3EncryptedUserName, npSecuritySnmpV3AuthKeyPassPhrase
        and npSecuritySnmpV3PrivKeyPassPharse have been set."
::=  {  npSecurity  13  }

npSecuritySnmpV3PassPhrase	OBJECT-TYPE
        SYNTAX			INTEGER  { key ( 0 ), passphrase ( 1 ) }
        MAX-ACCESS		read-write
        STATUS			current
        DESCRIPTION
        "Indicates whether npSecuritySnmpV3AuthKeyPassPhrase and npSecuritySnmpV3PrivKeyPassPharse OIDs
        will have Passphrase or key value.
        Key Value    0
        Passphrase   1
        "
::=  {  npSecurity  46 }

npSecuritySnmpV3PasswordComplexity	OBJECT-TYPE
        SYNTAX				INTEGER{ disabled ( 0 ) , enabled ( 1 )}
        MAX-ACCESS			read-write
        STATUS				current
        DESCRIPTION
        "Enables/Disables the complexity check on Authentication passphrase used while creating
        the SNMPv3 init account using EWS or SNMPv1/v2.
        Default value: disabled(0)
        If complexity check is enabled, following rules must be met for a passphrase to be considered valid:
        1) Passwords may not contain the snmpv3 init account username value. (case insensitive compare)
        2) The password must contain characters from three of the following four categories:
        a) Uppercase letters of European languages (A through Z, with diacritic marks, Greek and Cyrillic characters)
        b) Lowercase letters of European languages (a through z, sharp-s, with diacritic marks, Greek and Cyrillic characters)
        c) Base 10 digits (0 through 9)
        d) Non-alphanumeric characters (special characters = '!<double quotes>#$%&'()*+,-./:;<=>?@[\]^_`{|}~ ')
        "
::= { npSecurity  73  }

npSecuritySnmpV3PrivAlgorithm	OBJECT-TYPE
        SYNTAX			INTEGER  { des ( 2 ), aes-128 ( 3 ) }
        MAX-ACCESS		read-write
        STATUS			current
        DESCRIPTION
        "Indicates the Privacy Algorithm used.
        It can have the value DES or AES-128.
        This key will have a default value set to DES.
        The following values are defined:
        DES       2 (Default)
        AES-128   3
        "
::=  {  npSecurity  45 }

npSecuritySnmpV3PrivKeyPassPhrase	OBJECT-TYPE
        SYNTAX			OCTET STRING  ( SIZE ( 256 ) )
        MAX-ACCESS		write-only
        STATUS			current
        DESCRIPTION
        "The encrypted SNMPv3 Privacy passphrase or key.
        Use the npSecurityPublicKey to encrypt this value.
        When setting this object, all three user account objects (npSecuritySnmpV3EncryptedUserName,
        npSecuritySnmpV3AuthKeyPassPhrase, and npSecuritySnmpV3PrivKeyPassPhrase) should also be set in
        the same multi-varbind request.
        Implementations may accept the objects in separate SNMP requests, or they may return a inconsistentValue (12)
        failure to indicate that other objects are required.
        If setting the objects individually is allowed, the User Account will not be installed until after all three
        objects have been set.
        The other OID's related to SNMPv3 encryption are
        npSecuritySnmpV3PrivAlgorithm and npSecuritySnmpV3PassPhrase, please ensure that they are set appropriately.
        This OID can only be SET if the inital SNMP V3 account is not created
        (i.e. the value of npCtlSnmpV3InitAccount is 0)
        The values of npSecuritySnmpV3PrivAlgorithm and npSecuritySnmpV3PassPhrase must be set appropriately
        before setting the value of this OID.
        "
::=  {  npSecurity  15  }

npSecuritySslEncryptionStrength	OBJECT-TYPE
        SYNTAX			INTEGER  { low ( 1 ) , medium ( 2 ) , high ( 3 ) }
        MAX-ACCESS		read-write
        STATUS			current
        DESCRIPTION
        "The SSL Encryption Strength.
        Setting to Low, Medium or High decides the set of Cipher Suites that
        would be supported by the device."
::=  {  npSecurity  40  }

npSecuritySslRedirection	OBJECT-TYPE
        SYNTAX			INTEGER  { redirectionEnabled ( 1 ) , redirectionDisabled ( 2 ) }
        MAX-ACCESS		read-write
        STATUS			current
        DESCRIPTION
        "Setting this object causes the SSL redirection connection
        to be enabled or disabled."
::=  {  npSecurity  23  }

npSecurityTLSCiphers		OBJECT-TYPE
        SYNTAX		OCTET STRING  ( SIZE ( 1..200) )
        MAX-ACCESS          read-write
        STATUS              current
        DESCRIPTION
        "
        Used to explicitly configure the TLS ciphers that would be supported by the device.
        This OID is added because the current cipher categorization into LOW-MEDIUM-HIGH is fading away.
        Following are some of the scenarios where explicit configuration of allowed ciphers are required:
        Scenario 1) A customer may need HIGH encryption strength ciphers only, but for interoperability
        they may need to enable specific LOW/MEDIM cipher.
        Eg - RC4 which is a LOW Strength cipher is required for interoperability with Windows when HIGH encryption strength is set.
        Scenario 2) Customers may want to disable specific ciphers as and when security vulnerabilities
        are detected in them.
        The current list of ciphers and their standard Cipher Suite Values:
        |----------------------------------------------------------------------------------------------------|
        |Name(OpenSSL)     |NIST Name                       |Cipher Suite|FIPS 140-2 |Supported in           |
        |                                                   |Value       |Compliant  |TLS protocol versions  |
        |----------------------------------------------------------------------------------------------------|
        |AES256-GCM-SHA384 |TLS_RSA_WITH_AES_256_GCM_SHA384 |{0x009D}    |   Yes     |TLS 1.2                |
        |AES256-SHA256     |TLS-RSA-WITH-AES-256-CBC-SHA256 |{0x003D}    |   Yes     |TLS 1.0/TLS 1.1/TLS 1.2|
        |AES256-SHA        |TLS-RSA-WITH-AES-256-CBC-SHA    |{0x0035}    |   Yes     |TLS 1.0/TLS 1.1/TLS 1.2|
        |DES-CBC3-SHA      |TLS-RSA-WITH-3DES-EDE-CBC-SHA   |{0x000A}    |   Yes     |TLS 1.0/TLS 1.1/TLS 1.2|
        |AES128-GCM-SHA256 |TLS_RSA_WITH_AES_128_GCM_SHA256 |{0x009C}    |   Yes     |TLS 1.2                |
        |AES128-SHA256     |TLS-RSA-WITH-AES-128-CBC-SHA256 |{0x003C}    |   Yes     |TLS 1.0/TLS 1.1/TLS 1.2|
        |AES128-SHA        |TLS-RSA-WITH-AES-128-CBC-SHA    |{0x002F}    |   Yes     |TLS 1.0/TLS 1.1/TLS 1.2|
        |RC4-SHA           |TLS-RSA-WITH-RC4-128-SHA        |{0x0005}    |   No      |TLS 1.0/TLS 1.1/TLS 1.2|
        |RC4-MD5           |TLS-RSA-WITH-RC4-128-MD5        |{0x0004}    |   No      |TLS 1.0/TLS 1.1/TLS 1.2|
        |----------------------------------------------------------------------------------------------------|
        SNMP Operations:
        SNMPGet would return the a comma separated list of Cipher Suite Values configured.
        SNMPSet should be performed with comma separated list of Cipher Suite Values.
        Eg: To configure AES256-GCM-SHA384 and AES256-SHA256,set has to be performed with '0x009D,0x003D'
        Note: No comma required for single OID[Neeraj Gupta: ]  cipher suite.
        Errors returned:
        BAD VALUE(v1) or WRONG VALUE(v2/v3) will be returned when invalid/unsupported cipher OIDs are configured
        GENERIC ERROR will be returned and the npSecurityOpenSSLFIPSErrorTable will be updated with
        the appropriate error bit in the following cases
        1) TLS 1.2 is disabled and user tries to configure ciphers supported only with TLS 1.2.
        2) FIPS 140-2 is enabled and user tries to configure ciphers not allowed in FIPS 140-2 .
        "
::=  {  npSecurity  74 }

npSecurityTLSCiphersSupported		OBJECT-TYPE
        SYNTAX			OCTET STRING  ( SIZE ( 0 .. 200  ) )
        MAX-ACCESS		read-only
        STATUS			current
        DESCRIPTION
        "Used to explicitly show all the  TLS ciphers  that are supported by the device.
        The current list of ciphers and their standard Cipher Suite Values:
        |----------------------------------------------------------------------------------------------------|
        |Name(OpenSSL)     |NIST Name                       |Cipher Suite|FIPS 140-2 |Supported in           |
        |                                                   |Value       |Compliant  |TLS protocol versions  |
        |----------------------------------------------------------------------------------------------------|
        |AES256-GCM-SHA384 |TLS_RSA_WITH_AES_256_GCM_SHA384 |{0x009D}    |   Yes     |TLS 1.2                |
        |AES256-SHA256     |TLS-RSA-WITH-AES-256-CBC-SHA256 |{0x003D}    |   Yes     |TLS 1.0/TLS 1.1/TLS 1.2|
        |AES256-SHA        |TLS-RSA-WITH-AES-256-CBC-SHA    |{0x0035}    |   Yes     |TLS 1.0/TLS 1.1/TLS 1.2|
        |DES-CBC3-SHA      |TLS-RSA-WITH-3DES-EDE-CBC-SHA   |{0x000A}    |   Yes     |TLS 1.0/TLS 1.1/TLS 1.2|
        |AES128-GCM-SHA256 |TLS_RSA_WITH_AES_128_GCM_SHA256 |{0x009C}    |   Yes     |TLS 1.2                |
        |AES128-SHA256     |TLS-RSA-WITH-AES-128-CBC-SHA256 |{0x003C}    |   Yes     |TLS 1.0/TLS 1.1/TLS 1.2|
        |AES128-SHA        |TLS-RSA-WITH-AES-128-CBC-SHA    |{0x002F}    |   Yes     |TLS 1.0/TLS 1.1/TLS 1.2|
        |RC4-SHA           |TLS-RSA-WITH-RC4-128-SHA        |{0x0005}    |   No      |TLS 1.0/TLS 1.1/TLS 1.2|
        |RC4-MD5           |TLS-RSA-WITH-RC4-128-MD5        |{0x0004}    |   No      |TLS 1.0/TLS 1.1/TLS 1.2|
        |----------------------------------------------------------------------------------------------------|
        Get will return a comma separated list of all Cipher suite values supported on device.
        Example  0x009d,0x003d,0x0035,0x000a,0x009c,0x003c,0x002f,0x0005,0x0004,0x0009"
::=  {  npSecurity  75  }

npSecurityWirelessDirectEncryptedPassPhrase		OBJECT-TYPE
        SYNTAX			OCTET STRING  ( SIZE ( 1 .. 64  ) )
        MAX-ACCESS		write-only
        STATUS			current
        DESCRIPTION
        "
        The WPA2 Passphrase or pre-shared key for secure Wireless Direct.
        The values allowed are 8 to 63 printable ASCII characters for passphrase
        or a 64 character hex value for pre-shared key.
        Use npSecurityPublicKey to encrypt this value.
        "
::=  { npSecurity  55 }

npSysCardServices1	OBJECT-TYPE
        SYNTAX			Integer32
        MAX-ACCESS		read-only
        STATUS			current
        DESCRIPTION
        "This object is a bitmap showing what services are available
        on the card.
        Bit  0 - IPX/SPX/NCP protocol stack
        Bit  1 - IP/TCP protocol stack
        Bit  2 - LLC/DLC protocol stack
        Bit  3 - Ethertalk protocol stack
        Bit  4 - IPv6 protocol stack
        Bit  5 - IPSec protocol stack
        Bits  6 - 11 Reserved
        Bit 12 - LPD print services
        Bit 13 - FTP print services
        Bit 14 - Port 9100 print services
        Bit 15 - IPP print services
        Bits 16 - 23 Reserved
        Bit 24 - Queue Server Bindery
        Bit 25 - Queue Server NDS
        Bit 26 - Remote Printer
        Bit 27 - SPX Direct Mode
        Bit 28 - DLC Print Services
        Bit 29 - EtherTalk Print Services
        Bits 30 - 31 Reserved"
::=  {  npSys  16  }

npSysCardServices2	OBJECT-TYPE
        SYNTAX			Integer32
        MAX-ACCESS		read-only
        STATUS			current
        DESCRIPTION
        "This object is a bitmap showing what services are available
        on the card.
        Bit  0 - XIP2
        Bit  1 - PML Get/Set
        Bit  2 - PML Traps
        Bit  3 - Scan to Web Browser
        Bit  4 - Scan to Email
        Bit  5 - MFP Scan Support
        Bits  6 - 11 Reserved
        Bit 12 - Telnet API
        Bit 13 - Web API
        Bit 14 - SNMP V2
        Bit 15 - SNMP Traps
        Bit 16 - Download
        Bit 17 - TFTP
        Bit 18 - RCFG
        Bit 19 - SLP
        Bit 20 - Syslog
        Bit 21 - DHCP
        Bit 22 - BOOTP
        Bit 23 - RARP
        Bit 24 - SNMP V3
        Bit 25 - SSL Functionality
        Bit 26 - Auto IP
        Bit 27 - SNMP V3 SHA-1 & AES-128 support.
        Bits 28 - 31 Reserved"
::=  {  npSys  17  }

npSysCardServices3	OBJECT-TYPE
        SYNTAX			Integer32
        MAX-ACCESS		read-only
        STATUS			current
        DESCRIPTION
        "This object is a bitmap showing what services are available
        on the card.
        Bit  0 - 100T
        Bit  1 - Token Ring 802.5
        Bit  2 - 802.11b
        Bit  3 - 80211.a
        Bit  4 - Bluetooth
        Bits 5 - 11 Reserved
        Bit  12 -  EIO. For embedded Jetdirect this bit will be 1.
        Bit  13 - LIO
        Bit  14 - USB
        Bit  15 - Firewire
        Bit  16 - TCP Download
        Bits 17 - 31 Reserved"
::=  {  npSys  22  }

npSysModelNumber	OBJECT-TYPE
        SYNTAX			OCTET STRING  ( SIZE ( 6  ) )
        MAX-ACCESS		read-only
        STATUS			current
        DESCRIPTION
        "The HP model number of the device."
::=  {  npSys  10  }

npTcpAppSyslogPriority		OBJECT-TYPE
        SYNTAX		Integer32  ( 0 .. 8  )
        MAX-ACCESS	read-write
        STATUS		current
        DESCRIPTION "Priority below which the syslog messages will
        not be sent.
        Valid priority levels = 0 through 7.
        Disabled = 8."
::=  {  npTcp  12  }

npTcpSyslogMax			OBJECT-TYPE
        SYNTAX		Integer32  ( 0 .. 1000  )
        MAX-ACCESS	read-write
        STATUS		current
        DESCRIPTION "Maximum number of syslog packets to be sent
        per minute. 0 = Disabled."
::=  {  npTcp  11  }

npWebCheckACLforHTTP		OBJECT-TYPE
        SYNTAX		Integer32  ( 0 .. 1  )
        MAX-ACCESS	read-write
        STATUS		current
        DESCRIPTION "Configure checking of HTTP web connections against Access Control List.
        (0) = Disable ACL checking
        (1) = Enable ACL checking"
::=  {  npWeb  17  }

npWebProxyServerId	OBJECT-TYPE
        SYNTAX			OCTET STRING  ( SIZE ( 0 .. 255  ) )
        MAX-ACCESS		read-write
        STATUS			current
        DESCRIPTION
        "IP address or hostname of web proxy server."
::=  {  npWeb  12  }

npWebProxyServerPort	OBJECT-TYPE
        SYNTAX			Integer32
        MAX-ACCESS		read-write
        STATUS			current
        DESCRIPTION
        "IP port of web proxy server"
::=  {  npWeb  13  }

npWebProxyUserName	OBJECT-TYPE
        SYNTAX			OCTET STRING  ( SIZE ( 0 .. 64  ) )
        MAX-ACCESS		read-write
        STATUS			current
        DESCRIPTION
        "Proxy web user identification"
::=  {  npWeb  14  }

npWebProxyUserPasswd	OBJECT-TYPE
        SYNTAX			OCTET STRING  ( SIZE ( 0 .. 32  ) )
        MAX-ACCESS		read-write
        STATUS			current
        DESCRIPTION
        "Proxy web user password"
::=  {  npWeb  15  }

office-quality-pdl-display-tag		OBJECT-TYPE
        SYNTAX     INTEGER {
        cLaserQualityNormalMode(1000),
        cLaserQualityBestMode(1002),
        cLaserQualityDraftMode(1003),
        cLaserQualityMaximumMode(1004),
        cLaserQualityEconoMode(1005),
        cInkQualityDraftMode(3000),
        cInkQualityNormalMode(3001),
        cInkQualityBestMode(3002),
        cInkQualityMaximumMode(3003)
        }
        ACCESS     read-only
        STATUS     optional
        DESCRIPTION "Returns an Enum corresponding to the Description used by the client to provide a display string of quality attributes associated with Office Quality."
::= { office-quality-pdl 3 }

office-quality-pdl-hint-tag		OBJECT-TYPE
        SYNTAX     INTEGER {
        cLaserQualityNormalColorHint(2000),
        cLaserQualityNormalMonoHint(2001),
        cLaserQualityBestHint(2002),
        cLaserQualityDraftHint(2003),
        cLaserQualityMaximumHint(2004),
        cLaserQualityEconoHint(2005),
        cInkQualityDraftHint(4000),
        cInkQualityNormalHint(4005),
        cInkQualityBestHint(4010),
        cInkQualityMaximumHint(4015)
        }
        ACCESS     read-only
        STATUS     optional
        DESCRIPTION "Returns an Enum corresponding to the Description used by the client to provide underlying technology behind print quality such as ImageREt."
::= { office-quality-pdl 2 }

office-quality-pdl-optimum-resolution		OBJECT-TYPE
        SYNTAX	    INTEGER {
        e150(1),
        e300(2),
        e600(3),
        e1200(4)
        }
        ACCESS      read-only
        STATUS      optional
        DESCRIPTION "Indicates the current DPI option selected for the office quality draft.
        Reference resolution at the bottom of the mib for latest enumeration information."
::= { office-quality-pdl 1 }

pcl-total-page-count OBJECT-TYPE
        SYNTAX  INTEGER
        ACCESS  read-only
        STATUS  optional
        DESCRIPTION
        "Total number of PCL pages printed by the device.
        Additional information:
        The page count is incremented when a sheet of media is pulled from an input
        tray. A duplex printed sheet will cause this counter to be incremented by
        two."
::= { pdl-pcl 5 }

pjl-device-access		OBJECT-TYPE
        SYNTAX     INTEGER {
        eDisabled(1),
        eEnabled(2)
        }
        ACCESS     read-write
        STATUS     optional
        DESCRIPTION "This object is used to enable or disable PJL device attendance
        commands,SNMP passthrough commands and environment commands
        which affect persistent settings on the device.These include
        OPMSG,RDYMSG,STMSG,DMINFO,DMCMD, DEFAULT,INITIALISE and SET on
        default same-as-current PJL variables.By default this object is
        enabled."
::= { pjl 4 }

postscript-total-page-count OBJECT-TYPE
        SYNTAX  INTEGER
        ACCESS  read-only
        STATUS  optional
        DESCRIPTION
        "Total number of PostScript pages printed by the device."
::= { pdl-postscript 5 }

ppmGeneralNaturalLanguage OBJECT-TYPE
        SYNTAX      SnmpAdminString (SIZE (0..63))
        MAX-ACCESS  read-only
        STATUS      current
        DESCRIPTION
        "The natural language tag (RFC 3066), specified in US-ASCII, for
        all localized text string objects defined in this MIB (syntax of
        'SnmpAdminString'), or the empty string if not specified.  For
        example, 'fr-CH' (French as written in Switzerland).
        Compatibility Note:  At the time of publication of this MIB,
        language tags are restricted to US-ASCII.  In order to support
        possible future evolution of languages tags (in a successor to
        RFC 3066) to allow non-ASCII characters, this object has been
        defined with a syntax of UTF-8 (RFC 3629).
        This natural language tag is necessary for support of correct
        glyph selection for text display, for support of text-to-
        speech, for support of correct sorting of text values, etc.
        If this object is empty, then the natural language for all
        localized text string objects in this MIB MUST default to
        'en-US' (US English)."
        REFERENCE
        "prtGeneralCurrentLocalization in IETF Printer MIB (RFC
        1759/3805).
        jobNaturalLanguageTag in IETF Job Monitoring MIB (RFC 2707)."
        DEFVAL      { ''H }                 -- no natural language tag
::= { ppmGeneral 1 }

ppmGeneralNumberOfPorts OBJECT-TYPE
        SYNTAX      Gauge32
        MAX-ACCESS  read-only
        STATUS      current
        DESCRIPTION
        "The number of printer ports supported on this network system,
        i.e., the number of entries in the 'ppmPortTable' below, or
        zero if no printer ports are currently configured."
        DEFVAL      { 0 }                   -- no printer ports configured
::= { ppmGeneral 3 }

ppmGeneralNumberOfPrinters OBJECT-TYPE
        SYNTAX      Gauge32
        MAX-ACCESS  read-only
        STATUS      current
        DESCRIPTION
        "The number of printers supported on this network system,
        i.e., the number of entries in the 'ppmPrinterTable' below, or
        zero if no printers are currently configured."
        DEFVAL      { 0 }                   -- no printers configured
::= { ppmGeneral 2 }

ppmPortEnabled OBJECT-TYPE
        SYNTAX      TruthValue
        MAX-ACCESS  read-only
        STATUS      current
        DESCRIPTION
        "The current administrative configuration mode for this port.
        If this object is 'false', then applications MUST NOT attempt
        installation of this port and SHOULD NOT attempt print job
        submission to this port.
        If this object is 'true', then the port is currently enabled.
        If this object is 'false', then the port is currently disabled."
        REFERENCE
        "ppmPortProtocolType and ppmPortHrDeviceIndex."
        DEFVAL      { false }               -- port disabled
::= { ppmPortEntry 2 }

ppmPortLprByteCountEnabled OBJECT-TYPE
        SYNTAX      TruthValue
        MAX-ACCESS  read-only
        STATUS      current
        DESCRIPTION
        "The current LPR byte counting mode for this port if applicable.
        If the value of 'ppmPortProtocolType' is NOT 'chLPDServer(8)',
        then monitoring applications MUST ignore the value of this
        object.
        If this object is 'true', then LPR byte counting is enabled.
        If this object is 'false', then LPR byte counting is disabled."
        REFERENCE
        "IETF Line Printer Daemon Protocol (RFC 1179)."
        DEFVAL      { false }               -- LPR byte counting disabled
::= { ppmPortEntry 9 }

ppmPortName OBJECT-TYPE
        SYNTAX      SnmpAdminString (SIZE (0..127))
        MAX-ACCESS  read-only
        STATUS      current
        DESCRIPTION
        "A user friendly name for this port that may be used to
        facilitate user selection of a port on a multi-port network
        system, in the locale specified by 'ppmGeneralNaturalLanguage'.
        This port name may contain non-ASCII characters that are NOT
        allowed in a URI (RFC 3986) without percent-encoding.
        The value of this object SHOULD be unique across all ports on
        this network system and SHOULD be meaningful to end users
        (e.g., 'PrinterXYZ-LPR-Duplex').
        The value of this object SHOULD be set by an out-of-band method
        (e.g., local console) during installation (by the vendor or site
        administrator) and SHOULD NOT be subsequently modified, so that
        the value can be used as a static key for access to the port.
        The charset of this text string object is UTF-8 (RFC 3629), in
        order to support names that cannot be represented in US-ASCII."
        REFERENCE
        "prtChannelInformation in IETF Printer MIB v2 (RFC 3805)."
        DEFVAL      { ''H }                 -- port name not specified
::= { ppmPortEntry 3 }

ppmPortProtocolAltSourceEnabled OBJECT-TYPE
        SYNTAX      TruthValue
        MAX-ACCESS  read-only
        STATUS      current
        DESCRIPTION
        "The alternate transport source port mode for this protocol.
        If this object is 'true', then transport source ports outside
        the standard range MAY be used (e.g., LPR source port standard
        range is defined in RFC 1179 to be '721' to '731', inclusive).
        If this object is 'false', then transport source ports outside
        the standard range MUST NOT be used (to avoid protocol
        errors)."
        REFERENCE
        "IETF Line Printer Daemon Protocol (RFC 1179)."
        DEFVAL      { false }               -- alt source ports disabled
::= { ppmPortEntry 7 }

ppmPortProtocolTargetPort OBJECT-TYPE
        SYNTAX      Integer32 (0..65535)
        MAX-ACCESS  read-only
        STATUS      current
        DESCRIPTION
        "The transport (TCP, UDP, etc.) target port number for this
        protocol, i.e., an alternate port from the protocol default, or
        zero if not specified (use protocol default).  This object MAY
        be used for any print protocol (from the Internet, NetWare,
        AppleTalk, or other protocol suite).
        If this object is zero, then the actual target port number is
        the default port for the specified 'ppmPortProtocolType' (e.g.,
        'chPort9100(11)' uses '9100').
        If this object is non-zero, then it SHOULD NOT conflict with the
        default (e.g., IANA-registered) target port implied by the value
        of 'ppmPortProtocolType' or the explicit transport target port
        specified in 'ppmPortServiceNameOrURI'.  In case of conflict,
        the URI value in 'ppmPortServiceNameOrURI' is authoritative
        (e.g., 'ipp://example.com:631/~smith/printer').
        If 'ppmPortProtocolType' is 'chLPDServer(8)', then this object
        MUST be ignored (because LPR target port is fixed at '515')."
        REFERENCE
        "IETF Line Printer Daemon Protocol (RFC 1179)."
        DEFVAL      { 0 }                   -- target port not specified
::= { ppmPortEntry 6 }

ppmPortProtocolType OBJECT-TYPE
        SYNTAX      Integer32 (0..2147483647)
        MAX-ACCESS  read-only
        STATUS      current
        DESCRIPTION
        "The protocol type of this printer port, specified as a value
        from 'PrtChannelTypeTC' in the IANA Printer MIB (e.g.,
        'chLPDServer(8)' for LPR (RFC 1179) or 'chPort9100(11)' for
        Raw), or zero if not specified.
        Compatibility Note:  The value of zero is NOT registered in the
        IANA Printer MIB.  It is an out-of-band value.  Thus the syntax
        of this object is NOT specified as 'PrtChannelTypeTC'.
        Systems that do NOT implement IETF Printer MIB v2 (RFC 3805)
        SHOULD use 'chPort9100(11)' for Raw printing (with an alternate
        port in 'ppmPortProtocolTargetPort', if necessary), because
        'chPortTCP(37)' and 'chBidirPortTCP(38)' are NOT defined in
        IETF Printer MIB v1 (RFC 1759).
        Systems that do implement the IETF Printer MIB v2 (RFC 3805)
        MAY instead use 'chPortTCP(37)' or 'chBidirPortTCP(38)' for Raw
        printing, because 'chPort9100(11)' is DEPRECATED in IETF
        Printer MIB v2.
        Systems that implement any version of the IETF Printer MIB
        (RFC 1759/3805) SHOULD use the same value of protocol type for
        this port in the 'prtChannelTable', so monitoring applications
        MAY search for more channel information and status."
        REFERENCE
        "PrtChannelTypeTC in IANA Printer MIB (RFC 3805 and
        http://www.iana.org/assignments/ianaprinter-mib).
        prtChannelType in IETF Printer MIB (RFC 1759/3805)."
        DEFVAL      { 0 }                   -- protocol type not specified
::= { ppmPortEntry 5 }

ppmPortPrtChannelIndex OBJECT-TYPE
        SYNTAX      Integer32 (0..65535)
        MAX-ACCESS  read-only
        STATUS      current
        DESCRIPTION
        "The value of 'prtChannelIndex' in IETF Printer MIB
        (RFC 1759/3805) that corresponds to this printer port, or zero
        if not specified.
        Compatibility Note:  The value of zero is NOT valid for
        'prtChannelIndex'.  It is an out-of-band value.
        Systems that implement any version of the IETF Printer MIB
        (RFC 1759/3805) SHOULD correctly implement this object, so
        monitoring applications MAY search for print channel information
        and status.
        If this object is zero, then monitoring applications MUST NOT
        attempt print channel status queries for this printer port."
        REFERENCE
        "prtChannelIndex, prtChannelIfIndex, prtChannelState, and
        prtChannelStatus in IETF Printer MIB (RFC 1759/3805)."
        DEFVAL      { 0 }                   -- no print channel index
::= { ppmPortEntry 8 }

ppmPortServiceNameOrURI OBJECT-TYPE
        SYNTAX      SnmpAdminString (SIZE (0..255))
        MAX-ACCESS  read-only
        STATUS      current
        DESCRIPTION
        "The service name or URI for this port, specified in UTF-8 (RFC
        3629), in the locale specified by 'ppmGeneralNaturalLanguage'.
        The service name is typically a queue name.
        Compatibility Note:  At the time of publication of this MIB,
        the Microsoft tools do not support LPR queue names longer than
        32 characters.  Network administrators SHOULD NOT assign longer
        LPR queue names, to prevent interworking problems.
        Compatibility Note:  At the time of publication of this MIB,
        IETF URI Generic Syntax (RFC 3986) requires that all non-ASCII
        characters be percent-encoded, while IETF Internationalized
        Resource Identifiers (RFC 3987) permits native UTF-8 resource
        identifiers and supplies mappings to and from standard URI.
        In order to support current use of IRI and possible future
        evolution of URI (in a successor to RFC 3986) to allow non-ASCII
        characters, this object has been defined with a syntax of UTF-8
        (RFC 3629).
        Examples of well-formed service URI for print protocols
        include:
        - 'lpr://foo.example.com/public-printer' (where 'public-
        printer' is the LPR queue name portion)
        and
        - 'ipp://bar.example.com/printer/fox'
        If this object is non-empty, then it SHOULD NOT conflict with a
        the default (e.g., IANA-registered) or explicit transport target
        port specified in 'ppmPortProtocolTargetPort'.  In case of
        conflict, the URI value in 'ppmPortServiceNameOrURI' is
        authoritative (e.g., 'ipp://example.com:631/~smith/printer').
        If this object is empty and 'ppmPortProtocolType' is
        'chLPDServer(8)', the LPR queue name MUST default to 'LPR'."
        REFERENCE
        "IETF Line Printer Daemon Protocol (RFC 1179).
        'lpr:' URL scheme in IANA-registered SLP Printer Schema at
        http://www.iana.org/assignments/svrloc-templates/
        printer-uri in LDAP Printer Schema (RFC 3712).
        IPP/1.1: IPP URL Scheme (RFC 3510).
        printer-uri-supported in IPP/1.1 (RFC 2911)."
        DEFVAL      { ''H }                 -- no service name or URI
::= { ppmPortEntry 4 }

ppmPrinterHrDeviceIndex OBJECT-TYPE
        SYNTAX      Integer32 (0..2147483647)
        MAX-ACCESS  read-only
        STATUS      current
        DESCRIPTION
        "The value of 'hrDeviceIndex' in the IETF Host Resources MIB
        (RFC 1514/2790), or zero if not specified.  This value of
        'hrDeviceIndex' MAY be used for status queries for this printer
        if the value of 'ppmPrinterSnmpQueryEnabled' is 'true'.
        Compatibility Note:  The value of zero is NOT valid for
        'hrDeviceIndex'.  It is an out-of-band value.
        If this object is zero, then monitoring applications MUST NOT
        attempt status queries for this printer in the IETF Host
        Resources MIB (RFC 1514/2790) and/or IETF Printer MIB
        (RFC 1759/3805)."
        REFERENCE
        "hrDeviceStatus, hrPrinterStatus, hrPrinterDetectedErrorState
        in IETF Host Resources MIB (RFC 1514/2790).
        Section 2.2.13.2 'Overall Printer Status' and
        Appendix E 'Overall Printer Status Table' in IETF Printer MIB v2
        (RFC 3805)."
        DEFVAL      { 0 }                   -- no host device index
::= { ppmPrinterEntry 6 }

ppmPrinterIEEE1284DeviceId OBJECT-TYPE
        SYNTAX      OCTET STRING (SIZE (0..1023))
        MAX-ACCESS  read-only
        STATUS      current
        DESCRIPTION
        "The IEEE 1284 device ID for this printer, a set of capabilities
        (keys and values) specified in the US-ASCII charset and the
        format 'key1: value {, value }; ... keyN: value {,value };',
        as follows:
        (a) SPACE (0x20), TAB (0x09), VTAB (0x0B), CR (0x0D), NL (0x0A),
        and FF (0x0C) are allowed, but are ignored when parsing
        (b) other control characters (less than 0x20) MUST NOT be used
        (c) COLON (0x3A), COMMA (0x2C), and SEMICOLON (0x3B) are used as
        delimiters and MUST NOT be included in any key or value
        (d) each key MUST be separated from value(s) using COLON (0x3A)
        (e) multiple values MUST BE separated using COMMA (0x2C)
        (f) each capability MUST BE terminated using SEMICOLON (0x3B)
        (g) all printers MUST include the following capabilities
        - MANUFACTURER (or abbreviation MFG)
        - MODEL (or abbreviation MDL)
        (h) all printers MAY include the following capabilities
        - COMMAND SET (or abbreviation CMD)
        - COMMENT
        - ACTIVE COMMAND SET
        For example (actually all on one line of text):
        MANUFACTURER:ACME Manufacturing;
        COMMAND SET:PCL,PJL,PS,XHTML-Print+xml;
        MODEL:LaserBeam 9;
        COMMENT:Anything you like;
        ACTIVE COMMAND SET:PCL;
        The value of this object MUST exactly match the IEEE 1284-2000
        Device ID string, except that the length field MUST NOT be
        specified.  The value MUST be assigned by the Printer vendor
        and MUST NOT be localized by the Print Service.
        Compatibility Note:  At the time of publication of this MIB,
        IEEE device IDs are restricted to US-ASCII.  In order to support
        possible future evolution of IEEE device IDs (in a successor to
        IEEE 1284-2000) to allow non-ASCII characters, this object has
        been defined with a syntax of OCTET STRING to support the future
        use of UTF-8 (RFC 3629).
        If this object is empty, then the value of 'ppmPortProtocolType'
        for the selected port SHOULD be used to load a generic driver."
        REFERENCE
        "Section 7.6 of IEEE 1284-2000.
        printer-make-and-model in IPP/1.1 (RFC 2911)."
        DEFVAL      { ''H }                 -- no IEEE 1284 device ID
::= { ppmPrinterEntry 3 }

ppmPrinterName OBJECT-TYPE
        SYNTAX      SnmpAdminString (SIZE (0..127))
        MAX-ACCESS  read-only
        STATUS      current
        DESCRIPTION
        "A user friendly name for this printer that may be used to
        facilitate user selection of a printer supported by a network
        system, in the locale specified by 'ppmGeneralNaturalLanguage'.
        This printer name may contain non-ASCII characters that are NOT
        allowed in a URI (RFC 3986) without percent-encoding.
        Systems that implement the IETF Printer MIB v1 (RFC 1759) SHOULD
        implement this object as an augmentation to the Printer MIB v1.
        Systems that implement the IETF Printer MIB v2 (RFC 3805) MUST
        ensure that the value of this object is identical to the value
        of 'prtGeneralPrinterName' for each printer.
        The value of this object SHOULD be unique across all printers on
        this network system and SHOULD be meaningful to end users
        (e.g., 'PrinterXYZ').
        The value of this object SHOULD be set by an out-of-band method
        (e.g., local console) during installation (by the vendor or site
        administrator) and SHOULD NOT be subsequently modified, so that
        the value can be used as a static key for access to the printer.
        The charset of this text string object is UTF-8 (RFC 3629), in
        order to support names that cannot be represented in US-ASCII."
        REFERENCE
        "prtGeneralPrinterName in IETF Printer MIB v2 (RFC 3805).
        printer-name in IPP/1.1 (RFC 2911)."
        DEFVAL      { ''H }                 -- printer name not specified
::= { ppmPrinterEntry 2 }

ppmPrinterNumberOfPorts OBJECT-TYPE
        SYNTAX      Gauge32
        MAX-ACCESS  read-only
        STATUS      current
        DESCRIPTION
        "The number of printer ports supported on this network printer,
        i.e., the number of entries in the 'ppmPortTable' below with a
        first index of 'ppmPrinterIndex', or zero if no printer ports
        are currently configured."
        DEFVAL      { 0 }                   -- no printer ports configured
::= { ppmPrinterEntry 4 }

ppmPrinterPreferredPortIndex OBJECT-TYPE
        SYNTAX      Integer32 (0..2147483647)
        MAX-ACCESS  read-only
        STATUS      current
        DESCRIPTION
        "The value of 'ppmPortIndex' for the preferred port for this
        printer (configured by vendor or site administrator), or zero if
        not specified.
        Compatibility Note:  The value of zero is NOT valid for
        'ppmPortIndex'.  It is an out-of-band value.
        If this object is non-zero, then installation applications
        SHOULD default to this port in their user interface dialogue."
        REFERENCE
        "document-format-default in IPP/1.1 (RFC 2911)."
        DEFVAL      { 0 }                   -- no preferred port configured
::= { ppmPrinterEntry 5 }

ppmPrinterSnmpCommunityName OBJECT-TYPE
        SYNTAX      OCTET STRING (SIZE (0..255))
        MAX-ACCESS  read-only
        STATUS      current
        DESCRIPTION
        "The SNMP read community name, an opaque binary string, for
        access to status information in IETF Host Resources MIB (RFC
        1514/2790) and IETF Printer MIB (RFC 1759/3805) for this printer
        via the value of 'ppmPrinterHrDeviceIndex' (i.e., a 'MIB view'
        of these two MIBs).
        Security Warning:  Due to the widespread availability of free
        'packet sniffers' (network traffic snooping applications) and
        SNMP packet decoders, SNMP community names no longer offer even
        weak security.  This object SHOULD only be used to support 'MIB
        views'.  Implementations SHOULD use SNMPv3 security to protect
        network resources from unauthorized monitoring.
        If this object is empty, then the SNMP read community name for
        this printer (if any) SHOULD default to 'public' in US-ASCII."
        REFERENCE
        "snmpCommunityName in IETF SNMP Community MIB (RFC 3584)."
        DEFVAL      { ''H }                 -- no SNMP read community name
::= { ppmPrinterEntry 7 }

ppmPrinterSnmpQueryEnabled OBJECT-TYPE
        SYNTAX      TruthValue
        MAX-ACCESS  read-only
        STATUS      current
        DESCRIPTION
        "The status query mode for this printer, for queries by
        monitoring applications in the IETF Host Resources MIB
        (RFC 1514/2790) and/or IETF Printer MIB (RFC 1759/3805).
        If this object is 'true', then monitoring applications MAY
        attempt status queries for this printer in the IETF Host
        Resources MIB and/or IETF Printer MIB.
        If this object is 'false', then monitoring applications MUST
        NOT attempt status queries for this printer in the IETF Host
        Resources MIB and/or IETF Printer MIB."
        REFERENCE
        "ppmPrinterSnmpCommunityName."
        DEFVAL      { false }               -- SNMP status queries disabled
::= { ppmPrinterEntry 8 }

presentation-quality-pdl-display-tag		OBJECT-TYPE
        SYNTAX     INTEGER {
        cLaserQualityNormalMode(1000),
        cLaserQualityBestMode(1002),
        cLaserQualityDraftMode(1003),
        cLaserQualityMaximumMode(1004),
        cLaserQualityEconoMode(1005),
        cInkQualityDraftMode(3000),
        cInkQualityNormalMode(3001),
        cInkQualityBestMode(3002),
        cInkQualityMaximumMode(3003)
        }
        ACCESS     read-only
        STATUS     optional
        DESCRIPTION "Returns an Enum corresponding to the Description used by the client to provide a display string of quality attributes associated with Presentation Quality."
::= {presentation-quality-pdl 3}

presentation-quality-pdl-hint-tag		OBJECT-TYPE
        SYNTAX     INTEGER {
        cLaserQualityNormalColorHint(2000),
        cLaserQualityNormalMonoHint(2001),
        cLaserQualityBestHint(2002),
        cLaserQualityDraftHint(2003),
        cLaserQualityMaximumHint(2004),
        cLaserQualityEconoHint(2005),
        cInkQualityDraftHint(4000),
        cInkQualityNormalHint(4005),
        cInkQualityBestHint(4010),
        cInkQualityMaximumHint(4015)
        }
        ACCESS     read-only
        STATUS     optional
        DESCRIPTION "Returns an Enum corresponding to the Description used by the client to provide underlying technology behind print quality such as ImageREt."
::= { presentation-quality-pdl 2 }

presentation-quality-pdl-optimum-resolution	OBJECT-TYPE
        SYNTAX     INTEGER {
        e150(1),
        e300(2),
        e600(3),
        e1200(4)
        }
        ACCESS     read-only
        STATUS     optional
        DESCRIPTION "Indicates the current DPI option selected for the presentation quality best.
        Reference resolution at the bottom of the mib for latest enumeration information."
::= { presentation-quality-pdl 1 }

print-contract-version-major		OBJECT-TYPE
        SYNTAX	INTEGER
        ACCESS	read-only
        STATUS	optional
        DESCRIPTION "The Major Version of the current print contract that a product
        supports. -1 indicates no support."
::= { settings-prt-eng 41 }

print-contract-version-minor		OBJECT-TYPE
        SYNTAX	INTEGER
        ACCESS	read-only
        STATUS	optional
        DESCRIPTION "The Minor Version of the current print contract that a product
        supports. -1 indicates no support."
::= { settings-prt-eng 42 }

print-internal-page OBJECT-TYPE
        SYNTAX  INTEGER {
        eNotPrintingAnInternalPage(1),
        ePrintingAnUnknownInternalPage(2),
        eDeviceDemoPage1ConfigurationPage(3),
        eDeviceDemoPage2(4),
        eDeviceDemoPage5ErrorLog(7),
        eDeviceDemoPage6FileSystemDirectoryListing(8),
        eDeviceDemoPage7MenuMap(9),
        ePrintUsagePage(100),
        eSuppliesPage(101),
        eDevicePaperPathTest(254),
        eDevicePageRegistrationPage(255),
        ePrintQualityPages(256),
        ePCLFontList1(350),
        ePSFontList(450)
        }
        ACCESS  read-write
        STATUS  optional
        DESCRIPTION
        "Writing this object to a value other than
        eNotPrintingAnInternalPage causes the device to attempt to
        print an internally generated page. Reading this object
        provides an indication what internally generated page is
        currently being printed, if any. The actual page is device
        specific. Some devices may support continuously printing an
        internally generated page. Setting this object to
        eNotPrintingAnInternalPage terminates continuously printing
        internally generated pages. An internally generated page may
        not be allowed to be printed at any arbitrary time; under what
        conditions it will succeed or fail is device specific. If the
        device supports the requested page, but can not start printing
        the page when requested, the device will respond with
        <genErr>. RECOMMENDATION: If the
        device is ready (i.e. the NOT-READY-PRINTER object does not
        contain any items, except maybe being off-line) and is idle
        (i.e. the NOT-IDLE object does not contain any items), this
        request should always succeed. This provides a mechanism for
        driver writers to always determine if the action will succeed
        or not."
::= { test 2 }

print-quality-image-enhancement		OBJECT-TYPE
        SYNTAX      INTEGER {
        eFalse(1),
        eTrue(2)
        }
        ACCESS      read-only
        STATUS      optional
        DESCRIPTION "Indicates the supported image enhancement options supported by
        the product. This OID is a singly-indexed OID where the first
        index indicates the image enhancement options supported by the
        product. The format for the OID is as follows: 1.3.3.1.47.n
        where n is the image enhancement option. Image enhancement (n)
        is indexed as follows: eRGB_Theme (1), eCMYK_Theme (2),
        eAdvancedImageControl(3), eInkAdvancedControl(4) Reference
        image-enhancement at the bottom of the mib for latest
        enumeration information."
::= { settings-pdl 47 }

print-quality-process-black		OBJECT-TYPE
        SYNTAX	    INTEGER {
        eFalse(1),
        eTrue(2)
        }
        ACCESS      read-only
        STATUS      optional
        DESCRIPTION "Indicates whether or not the printer supports process black as
        a setting."
::= { settings-pdl 49 }

print-quality-square-resolution		OBJECT-TYPE
        SYNTAX      INTEGER {
        eFalse(1),
        eTrue(2)
        }
        ACCESS      read-only
        STATUS      optional
        DESCRIPTION "Indicates the supported DPI options supported by the product.
        This OID is a singly-indexed OID where the first index
        indicates the DPI options supported by the product. The format
        for the OID is as follows: 1.3.3.1.45.n where n is the DPI
        option. DPI option (n) is indexed as follows: e150(1), e300(2),
        e600(3), e1200(4) Reference resolution at the bottom of the mib
        for latest enumeration information."
::= { settings-pdl 45 }

printed-media-color-duplex-count OBJECT-TYPE
        SYNTAX  INTEGER
        ACCESS  read-only
        STATUS  optional
        DESCRIPTION
        "Total number of color duplex pages printed in this media size."
::= { printed-media-color-usage 3 }

printed-media-color-simplex-count OBJECT-TYPE
        SYNTAX  INTEGER
        ACCESS  read-only
        STATUS  optional
        DESCRIPTION
        "Total number of color simplex pages printed in this media
        size."
::= { printed-media-color-usage 1 }

printed-media-duplex-count OBJECT-TYPE
        SYNTAX  INTEGER(0..930576247)
        ACCESS  read-only
        STATUS  optional
        DESCRIPTION
        "Total number of duplex pages printed in this media size."
::= { printed-media-usage 3 }

printed-media-simplex-count OBJECT-TYPE
        SYNTAX  INTEGER(0..930576247)
        ACCESS  read-only
        STATUS  optional
        DESCRIPTION
        "Total number of simplex pages printed in this media size.
        Additional information:
        The 5 usage (simplex/duplex count, simplex/duplex click
        charge and paper size total) objects described here and
        below detail the usage for the printer for each paper
        size defined in the PCL Implementor's Guide and in the
        Media Size Table in the hpmib.txt.  The OID binding is
        based on the click attribute and paper size.
        For example:
        The format for the OID is as follows:
        3.4.1.5.x.y
        <-----> | |
        |    |  \
        /     |  paper size
        /       \
        PRINTER-CLICK_TOTALS ROOT   \
        OID                      click attribute 1..5
        x values are 1..5:
        1) simplex count
        2) simplex click charge
        3) duplex count
        4) duplex click charge
        5) printer or scanner paper size total (i.e. depends if the
        root OID is referrring to the printer or scanner).
        y : paper size as defined in the Media Size Table in the
        hpmib.txt "
::= { printed-media-usage 1 }

professional-quality-pdl-display-tag		OBJECT-TYPE
        SYNTAX     INTEGER {
        cLaserQualityNormalMode(1000),
        cLaserQualityBestMode(1002),
        cLaserQualityDraftMode(1003),
        cLaserQualityMaximumMode(1004),
        cLaserQualityEconoMode(1005),
        cInkQualityDraftMode(3000),
        cInkQualityNormalMode(3001),
        cInkQualityBestMode(3002),
        cInkQualityMaximumMode(3003)
        }
        ACCESS     read-only
        STATUS     optional
        DESCRIPTION "Returns an Enum corresponding to the Description used by the client to provide a display string of quality attributes associated with Professional Quality."
::= { professional-quality-pdl 3 }

professional-quality-pdl-hint-tag		OBJECT-TYPE
        SYNTAX     INTEGER {
        cLaserQualityNormalColorHint(2000),
        cLaserQualityNormalMonoHint(2001),
        cLaserQualityBestHint(2002),
        cLaserQualityDraftHint(2003),
        cLaserQualityMaximumHint(2004),
        cLaserQualityEconoHint(2005),
        cInkQualityDraftHint(4000),
        cInkQualityNormalHint(4005),
        cInkQualityBestHint(4010),
        cInkQualityMaximumHint(4015)
        }
        ACCESS     read-only
        STATUS      optional
        DESCRIPTION "Returns an Enum corresponding to the Description used by the client to provide underlying technology behind print quality such as ImageREt."
::= { professional-quality-pdl 2 }

professional-quality-pdl-optimum-resolution		OBJECT-TYPE
        SYNTAX     INTEGER {
        e150(1),
        e300(2),
        e600(3),
        e1200(4)
        }
        ACCESS     read-only
        STATUS     optional
        DESCRIPTION "Indicates the current DPI option selected for the professional quality normal.
        Reference resolution at the bottom of the mib for latest enumeration information."
::= { professional-quality-pdl 1 }

prtAlertAllEvents OBJECT-TYPE
        SYNTAX     Counter32
        MAX-ACCESS read-only
        STATUS     current
        DESCRIPTION
        "A running counter of the total number of alert event entries
        (critical and non-critical) that have been recorded in the
        alert table"
::= { prtGeneralEntry 19 }

prtAlertCode OBJECT-TYPE
        --  NOTE: In RFC 1759, the enumeration values were implicitly
        --  defined by this object.
        SYNTAX     PrtAlertCodeTC
        MAX-ACCESS read-only
        STATUS     current
        DESCRIPTION
        "See associated TEXTUAL-CONVENTION PrtAlertCodeTC.
        NOTE: The above description has been modified from RFC 1759
        for clarification."
::= { prtAlertEntry 7 }

prtAlertCriticalEvents OBJECT-TYPE
        SYNTAX     Counter32
        MAX-ACCESS read-only
        STATUS     current
        DESCRIPTION
        "A running counter of the number of critical alert events that
        have been recorded in the alert table.  The value of this object
        is RESET in the event of a power cycle operation (i.e., the
        value is not persistent."
::= { prtGeneralEntry 18 }

prtAlertDescription OBJECT-TYPE
        -- In RFC 1759, the SYNTAX was OCTET STRING.  This has been changed
        -- to a TC to better support localization of the object.
        SYNTAX     PrtLocalizedDescriptionStringTC
        MAX-ACCESS read-only
        STATUS     current
        DESCRIPTION
        "A description of this alert entry in the localization
        specified by prtGeneralCurrentLocalization.  The description is
        provided by the printer to further elaborate on the enumerated
        alert or provide information in the case where the code is
        classified as 'other' or 'unknown'.  The printer is required to
        return a description string but the string may be a null
        string."
::= { prtAlertEntry 8 }

prtAlertGroup OBJECT-TYPE
        --  NOTE: In RFC 1759, the enumeration values were implicitly
        --  defined by this object.
        SYNTAX     PrtAlertGroupTC
        MAX-ACCESS read-only
        STATUS     current
        DESCRIPTION
        "The type of sub-unit within the printer model that this alert
        is related.  Input, output, and markers are examples of printer
        model groups, i.e., examples of types of sub-units.  Wherever
        possible, these enumerations match the sub-identifier that
        identifies the relevant table in the printmib."
::= { prtAlertEntry 4 }

prtAlertGroupIndex OBJECT-TYPE
        -- NOTE: In RFC 1759, the range was not defined.
        SYNTAX     Integer32 (-1..2147483647)
        MAX-ACCESS read-only
        STATUS     current
        DESCRIPTION
        "The low-order index of the row within the table identified
        by prtAlertGroup that represents the sub-unit of the printer
        that caused this alert, or -1 if not applicable.  The
        combination of the prtAlertGroup and the prtAlertGroupIndex
        defines exactly which printer sub-unit caused the alert; for
        example, Input #3, Output#2, and Marker #1.  Every object in
        this MIB is indexed with hrDeviceIndex and optionally, another
        index variable.  If this other index variable is present in the
        table that generated the alert, it will be used as the value
        for this object.  Otherwise, this value shall be -1.
        NOTE: The above description has been modified from RFC 1759
        for clarification."
::= { prtAlertEntry 5 }

prtAlertIndex OBJECT-TYPE
        -- NOTE: In RFC 1759, the range was not defined.  The MAX-ACCESS has
        --       been changed from not accessible to allow the object to be
        --       included (as originally in RFC 1759) in the trap bindings.
        SYNTAX     Integer32 (1..2147483647)
        MAX-ACCESS read-only
        STATUS     current
        DESCRIPTION
        "The index value used to determine which alerts have been added
        or removed from the alert table.  This is an incrementing
        integer initialized to 1 when the printer is reset.  (i.e., The
        first event placed in the alert table after a reset of the
        printer shall have an index value of 1.)  When the printer adds
        an alert to the table, that alert is assigned the next higher
        integer value from the last item entered into the table.  If
        the index value reaches its maximum value, the next index value
        used must be 1.
        NOTE: The management application will read the alert table when
        a trap or event notification occurs or at a periodic rate and
        then parse the table to determine if any new entries were added
        by comparing the last known index value with the current
        highest index value.  The management application will then
        update its copy of the alert table.  When the printer discovers
        that an alert is no longer active, the printer shall remove the
        row for that alert from the table and shall reduce the number
        of rows in the table.  The printer may add or delete any number
        of rows from the table at any time.  The management station can
        detect when binary change alerts have been deleted by
        requesting an attribute of each alert, and noting alerts as
        deleted when that retrieval is not possible.  The objects
        'prtAlertCriticalEvents'and 'prtAlertAllEvents' in the
        'prtGeneralTable' reduce the need for management applications
        to scan the 'prtAlertTable'.
        NOTE: The above description has been modified from RFC 1759
        for clarification."
::= { prtAlertEntry 1 }

prtAlertLocation OBJECT-TYPE
        -- NOTE: In RFC 1759, the range was not defined.
        SYNTAX     Integer32 (-2..2147483647)
        MAX-ACCESS read-only
        STATUS     current
        DESCRIPTION
        "The sub-unit location that is defined by the printer
        manufacturer to further refine the location of this alert
        within the designated sub-unit.  The location is used in
        conjunction with the Group and GroupIndex values; for example,
        there is an alert in Input #2 at location number 7.  The value
        (-2) indicates unknown.
        NOTE: The above description has been modified from RFC 1759
        for clarification."
::= { prtAlertEntry 6 }

prtAlertSeverityLevel OBJECT-TYPE
        --  NOTE: In RFC 1759, the enumeration values were implicitly
        --  defined by this object.
        SYNTAX     PrtAlertSeverityLevelTC
        MAX-ACCESS read-only
        STATUS     current
        DESCRIPTION
        "The level of severity of this alert table entry.  The printer
        determines the severity level assigned to each entry into the
        table."
::= { prtAlertEntry 2 }

prtAlertTime OBJECT-TYPE
        SYNTAX     TimeTicks
        MAX-ACCESS read-only
        STATUS     current
        DESCRIPTION
        "The value of sysUpTime at the time that this alert was
        generated."
::= { prtAlertEntry 9 }

prtAlertTrainingLevel OBJECT-TYPE
        --  NOTE: In RFC 1759, the enumeration values were implicitly
        --  defined by this object.
        SYNTAX     PrtAlertTrainingLevelTC
        MAX-ACCESS read-only
        STATUS     current
        DESCRIPTION
        "See TEXTUAL-CONVENTION PrtAlertTrainingLevelTC.
        NOTE: The above description has been modified from RFC 1759
        for clarification."
::= { prtAlertEntry 3 }

prtChannelCurrentJobCntlLangIndex OBJECT-TYPE
        -- NOTE: In RFC 1759, the range was not defined.
        SYNTAX     Integer32 (0..65535)
        MAX-ACCESS read-write
        STATUS     current
        DESCRIPTION
        "The value of prtInterpreterIndex corresponding to the Control
        Language Interpreter for this channel.  This interpreter defines
        the syntax used for control functions, such as querying or
        changing environment variables and identifying job boundaries
        (e.g., PJL, PostScript, NPAP).  A value of zero indicates that
        there is no current Job Control Language Interpreter for this
        channel.
        NOTE: The above description has been modified from RFC 1759
        for clarification."
::= { prtChannelEntry 4 }

prtChannelDefaultPageDescLangIndex OBJECT-TYPE
        -- NOTE: In RFC 1759, the range was not defined.
        SYNTAX     Integer32 (0..65535)
        MAX-ACCESS read-write
        STATUS     current
        DESCRIPTION
        "The value of prtInterpreterIndex corresponding to the Page
        Description Language Interpreter for this channel.  This
        interpreter defines the default Page Description Language
        interpreter to be used for the print data unless the Control
        Language is used to select a specific interpreter (e.g., PCL,
        PostScript Language, auto-sense).  A value of zero indicates
        that there is no default page description language interpreter
        for this channel.
        NOTE: The above description has been modified from RFC 1759
        for clarification."
::= { prtChannelEntry 5 }

prtChannelIfIndex OBJECT-TYPE
        SYNTAX     InterfaceIndexOrZero   -- Was Integer32 in RFC 1759.
        MAX-ACCESS read-write
        STATUS     current
        DESCRIPTION
        "The value of ifIndex in the ifTable; see the Interfaces Group
        MIB [RFC2863] which corresponds to this channel.
        When more than one row of the ifTable is relevant, this is the
        index of the row representing the topmost layer in the
        interface hierarchy.  A value of zero indicates that no
        interface is associated with this channel.
        NOTE: The above description has been modified from RFC 1759
        for clarification."
::= { prtChannelEntry 7 }

prtChannelInformation OBJECT-TYPE
        SYNTAX     OCTET STRING (SIZE (0..255))
        MAX-ACCESS read-only
        STATUS     current
        DESCRIPTION
        "Auxiliary information to allow a printing application to use
        the channel for data submission to the printer.  An application
        capable of using a specific PrtChannelType should be able to
        use the combined information from the prtChannelInformation and
        other channel and interface group objects to 'bootstrap' its
        use of the channel.  prtChannelInformation is not intended to
        provide a general channel description, nor to provide
        information that is available once the channel is in use.
        The encoding and interpretation of the prtChannelInformation
        object is specific to channel type.  The description of each
        PrtChannelType enum value for which prtChannelInformation is
        defined specifies the appropriate encoding and interpretation,
        including interaction with other objects.  For channel types
        that do not specify a prtChannelInformation value, its value
        shall be null (0 length).
        When a new PrtChannelType enumeration value is registered, its
        accompanying description must specify the encoding and
        interpretation of the prtChannelInformation value for the
        channel type.  prtChannelInformation semantics for an existing
        PrtChannelType may be added or amended in the same manner as
        described in section 2.4.1 for type 2 enumeration values.
        The prtChannelInformation specifies values for a collection of
        channel attributes, represented as text according to the
        following rules:
        1. The prtChannelInformation is not affected by localization.
        2. The prtChannelInformation is a list of entries representing
        the attribute values.  Each entry consists of the following
        items, in order:
        a. A keyword, composed of alphabetic characters (A-Z, a-z)
        represented by their NVT ASCII [RFC854] codes, that
        identifies a channel attribute,
        b. The NVT ASCII code for an Equals Sign (=) (code 61) to
        delimit the keyword,
        c. A data value encoded using rules specific to the
        PrtChannelType to with the prtChannelInformation applies which
        must in no case allow an octet with value 10 (the NVT ASCII
        Line Feed code),
        d. the NVT ASCII code for a Line Feed character (code 10) to
        delimit the data value.
        No other octets shall be present.
        Keywords are case-sensitive.  Conventionally, keywords are
        capitalized (including each word of a multi-word keyword) and
        since they occupy space in the prtChannelInformation, they are
        kept short.
        3. If a channel attribute has multiple values, it is
        represented by multiple entries with the same keyword, each
        specifying one value. Otherwise, there shall be at most one
        entry for each attribute.
        4. By default, entries may appear in any order.  If there are
        ordering constraints for particular entries, these must be
        specified in their definitions.
        5. The prtChannelInformation value by default consists of text
        represented by NVT ASCII graphics character codes.  However,
        other representations may be specified:
        a. In cases where the prtChannelInformation value contains
        information not normally coded in textual form, whatever
        symbolic representation is conventionally used for the
        information should be used for encoding the
        prtChannelInformation value.  (For instance, a binary port value
        might be represented as a decimal number using NVT ASCII
        codes.)  Such encoding must be specified in the definition of
        the value.
        b. The value may contain textual information in a character set
        other than NVT ASCII graphics characters.  (For instance, an
        identifier might consist of ISO 10646 text encoded using the
        UTF-8 encoding scheme.)  Such a character set and its encoding
        must be specified in the definition of the value.
        6. For each PrtChannelType for which prtChannelInformation
        entries are defined, the descriptive text associated with the
        PrtChannelType enumeration value shall specify the following
        information for each entry:
        Title:        Brief description phrase, e.g.: 'Port name',
        'Service Name', etc.
        Keyword:      The keyword value, e.g.: 'Port' or 'Service'
        Syntax:       The encoding of the entry value if it cannot be
        directly represented by NVT ASCII.
        Status:       'Mandatory', 'Optional', or 'Conditionally
        Mandatory'
        Multiplicity: 'Single' or 'Multiple' to indicate whether the
        entry may be present multiple times.
        Description:  Description of the use of the entry, other
        information required to complete the definition
        (e.g.: ordering constraints, interactions between
        entries).
        Applications that interpret prtChannelInformation should ignore
        unrecognized entries, so they are not affected if new entry
        types are added."
::= { prtChannelEntry 9 }

prtChannelProtocolVersion OBJECT-TYPE
        SYNTAX     OCTET STRING (SIZE(0..63))
        MAX-ACCESS read-only
        STATUS     current
        DESCRIPTION
        "The version of the protocol used on this channel.  The format
        used for version numbering depends on prtChannelType."
::= { prtChannelEntry 3 }

prtChannelState OBJECT-TYPE
        --  NOTE: In RFC 1759, the enumeration values were implicitly
        --  defined by this object.
        SYNTAX     PrtChannelStateTC
        MAX-ACCESS read-write
        STATUS     current
        DESCRIPTION
        "The state of this print data channel.  The value determines
        whether control information and print data is allowed through
        this channel or not."
::= { prtChannelEntry 6 }

prtChannelStatus OBJECT-TYPE
        SYNTAX     PrtSubUnitStatusTC
        MAX-ACCESS read-only
        STATUS     current
        DESCRIPTION
        "The current status of the channel."
::= { prtChannelEntry 8 }

prtChannelType OBJECT-TYPE
        --  NOTE: In RFC 1759, the enumeration values were implicitly
        --  defined by this object.
        SYNTAX     PrtChannelTypeTC
        MAX-ACCESS read-only
        STATUS     current
        DESCRIPTION
        "The type of this print data channel.  This object provides the
        linkage to ChannelType-specific groups that may (conceptually)
        extend the prtChannelTable with additional details about that
        channel."
::= { prtChannelEntry 2 }

prtConsoleDisplayBufferText OBJECT-TYPE
        -- In RFC 1759, the SYNTAX was OCTET STRING.  This has been changed
        -- to a TC to better support localization of the object.
        SYNTAX     PrtConsoleDescriptionStringTC
        MAX-ACCESS read-write
        STATUS     current
        DESCRIPTION
        "The content of a line in the logical display buffer of
        the operator's console of the printer.  When a write
        operation occurs, normally a critical message, to one of
        the LineText strings, the agent should make that line
        displayable if a physical display is present.  Writing a zero
        length string clears the line.  It is an implementation-
        specific matter as to whether the agent allows a line to be
        overwritten before it has been cleared.  Printer generated
        strings shall be in the localization specified by
        prtConsoleLocalization.Management Application generated strings
        should be localized by the Management Application."
::= { prtConsoleDisplayBufferEntry 2 }

prtConsoleLocalization OBJECT-TYPE
        SYNTAX     Integer32 (1..65535)
        MAX-ACCESS read-write
        STATUS     current
        DESCRIPTION
        "The value of the prtLocalizationIndex corresponding to
        the language, country, and character set to be used for the
        console.  This localization applies both to the actual display
        on the console as well as the encoding of these console objects
        in management operations.  When an object's 'charset' is
        controlled by the value of prtConsoleLocalization, it MUST
        specify PrtConsoleDescriptionStringTC as its syntax.
        NOTE: The above description has been modified from RFC 1759
        for clarification."
::= { prtGeneralEntry 10 }

prtConsoleNumberOfDisplayLines OBJECT-TYPE
        SYNTAX     Integer32 (0..65535)
        MAX-ACCESS read-only
        STATUS     current
        DESCRIPTION
        "The number of lines on the printer's physical
        display.  This value is 0 if there are no lines on the
        physical display or if there is no physical display"
::= { prtGeneralEntry 11 }

prtCoverDescription OBJECT-TYPE
        -- In RFC 1759, the SYNTAX was OCTET STRING.  This has been changed
        -- to a TC to better support localization of the object.
        SYNTAX     PrtLocalizedDescriptionStringTC
        MAX-ACCESS read-only
        STATUS     current
        DESCRIPTION
        "The manufacturer provided cover sub-mechanism name in the
        localization specified by prtGeneralCurrentLocalization."
::= { prtCoverEntry 2 }

prtCoverStatus  OBJECT-TYPE
        -- NOTE: In RFC 1759, the enumeration values were implicitly defined
        -- by this object and are now defined in the IANA-PRINTER-MIB.  The
        -- new TC has defined "coverOpen" and "coverClosed" to replace
        -- "doorOpen" and "doorClosed" in RFC 1759.  A name change is not
        -- formally allowed per SMI rules, but was agreed to by the WG group
        -- since a door has a more restrictive meaning than a cover and
        -- Cover group is intended to support doors as a subset of covers.
        SYNTAX     PrtCoverStatusTC
        MAX-ACCESS read-only
        STATUS     current
        DESCRIPTION
        "The status of this cover sub-unit."
::= { prtCoverEntry 3 }

prtGeneralConfigChanges OBJECT-TYPE
        SYNTAX     Counter32
        MAX-ACCESS read-only
        STATUS     current
        DESCRIPTION
        "Counts configuration changes within the printer. A
        configuration change is defined to be an action that results in
        a change to any MIB object other than those that reflect status
        or level, or those that act as counters or gauges. In addition,
        any action that results in a row being added or deleted from
        any table in the Printer MIB is considered a configuration
        change. Such changes will often affect the capability of the
        printer to service certain types of print jobs. Management
        applications may cache infrequently changed configuration
        information about sub units within the printer. This object
        should be incremented whenever the agent wishes to notify
        management applications that any cached configuration
        information for this device is to be considered 'stale'. At
        this point, the management application should flush any
        configuration information cached about this device and fetch
        new configuration information.
        The following are examples of actions that would cause the
        prtGeneralConfigChanges object to be incremented:
        - Adding an output bin
        - Changing the media in a sensing input tray
        - Changing the value of prtInputMediaType
        Note that the prtGeneralConfigChanges counter would not be
        incremented when an input tray is temporarily removed to load
        additional paper or when the level of an input device changes.
        NOTE: The above description has been modified from RFC 1759
        for clarification."
::= { prtGeneralEntry 1 }

prtGeneralCurrentLocalization OBJECT-TYPE
        SYNTAX     Integer32 (1..65535)
        MAX-ACCESS read-write
        STATUS     current
        DESCRIPTION
        "The value of the prtLocalizationIndex corresponding to the
        current language, country, and character set to be used for
        localized string values that are identified as being dependent
        on the value of this object.  Note that this object does not
        apply to localized strings in the prtConsole group or to any
        object that is not explicitly identified as being localized
        according to prtGeneralCurrentLocalization.  When an object's
        'charset' is controlled by the value of
        prtGeneralCurrentLocalization, it MUST specify
        PrtLocalizedDescriptionStringTC as its syntax.
        NOTE: The above description has been modified from RFC 1759
        for clarification."
::= { prtGeneralEntry 2 }

prtGeneralCurrentOperator OBJECT-TYPE
        SYNTAX     OCTET STRING (SIZE(0..127))
        MAX-ACCESS read-write
        STATUS     current
        DESCRIPTION
        "The name of the person who is responsible for operating
        this printer.  It is suggested that this string include
        information that would enable other humans to reach the
        operator, such as a phone number.  As a convention to
        facilitate automatic notification of the operator by the
        agent or network management station, the phone number,
        fax number or email address should be indicated by the
        URL schemes 'tel:', 'fax:' and 'mailto:', respectively.
        If either the phone, fax, or email information is not
        available, then a line should not be included for this
        information.
        NOTE: For interoperability purposes, it is advisable to
        use email addresses formatted according to [RFC2822]
        requirements.
        NOTE: The above description has been modified from RFC 1759
        for clarification."
::= { prtGeneralEntry 4 }

prtGeneralPrinterName OBJECT-TYPE
        SYNTAX     OCTET STRING (SIZE (0..127))
        MAX-ACCESS read-write
        STATUS     current
        DESCRIPTION
        "An administrator-specified name for this printer.  Depending
        upon implementation of this printer, the value of this object
        may or may not be same as the value for the MIB-II 'SysName'
        object."
::= { prtGeneralEntry 16 }

prtGeneralReset OBJECT-TYPE
        -- NOTE: In RFC 1759, the enumeration values were implicitly defined
        -- by this object.
        SYNTAX     PrtGeneralResetTC
        MAX-ACCESS read-write
        STATUS     current
        DESCRIPTION
        "Setting this value to 'powerCycleReset', 'resetToNVRAM', or
        'resetToFactoryDefaults' will result in the resetting of the
        printer.  When read, this object will always have the value
        'notResetting(3)', and a SET of the value 'notResetting' shall
        have no effect on the printer.  Some of the defined values are
        optional.  However, every implementation must support at least
        the values 'notResetting' and 'resetToNVRAM'."
::= { prtGeneralEntry 3 }

prtGeneralSerialNumber OBJECT-TYPE
        SYNTAX     OCTET STRING (SIZE (0..255))
        MAX-ACCESS read-write
        STATUS     current
        DESCRIPTION
        "A recorded serial number for this device that indexes some
        type device catalog or inventory.  This value is usually set by
        the device manufacturer but the MIB supports the option of
        writing for this object for site-specific administration of
        device inventory or tracking."
::= { prtGeneralEntry 17 }

prtGeneralServicePerson OBJECT-TYPE
        SYNTAX     OCTET STRING (SIZE(0..127))
        MAX-ACCESS read-write
        STATUS     current
        DESCRIPTION
        "The name of the person responsible for servicing this
        printer.  It is suggested that this string include
        information that would enable other humans to reach the
        service person, such as a phone number.  As a convention
        to facilitate automatic notification of the operator by
        the agent or network management station, the phone
        number, fax number or email address should be indicated
        by the URL schemes 'tel:', 'fax:' and 'mailto:',
        respectively.  If either the phone, fax, or email
        information is not available, then a line should not
        be included for this information.
        NOTE: For interoperability purposes, it is advisable to use
        email addresses formatted per [RFC2822] requirements.
        NOTE: The above description has been modified from RFC 1759
        for clarification."
::= { prtGeneralEntry 5 }

prtInputCapacityUnit OBJECT-TYPE
        -- NOTE: In RFC 1759, the enumeration values were implicitly
        -- defined by this object.
        SYNTAX     PrtCapacityUnitTC
        MAX-ACCESS read-only
        STATUS     current
        DESCRIPTION
        "The unit of measurement for use in calculating and relaying
        capacity values for this input sub-unit."
::= { prtInputEntry 8 }

prtInputCurrentLevel OBJECT-TYPE
        -- NOTE: In RFC 1759, the range was not defined.
        SYNTAX     Integer32 (-3..2147483647)    -- in capacity units
        -- (PrtCapacityUnitTC).
        MAX-ACCESS read-write
        STATUS     current
        DESCRIPTION
        "The current capacity of the input sub-unit in input sub-unit
        capacity units (PrtCapacityUnitTC).  If this input sub-unit can
        reliably sense this value, the value is sensed by the printer
        and may not be changed by management requests; otherwise, the
        value may be written (by a Remote Control Panel or a Management
        Application).  The value (-1) means other and specifically
        indicates that the sub-unit places no restrictions on this
        parameter.  The value (-2) means unknown.  The value (-3) means
        that the printer knows that at least one unit remains."
::= { prtInputEntry 10 }

prtInputDefaultIndex OBJECT-TYPE
        SYNTAX     Integer32 (1..65535)
        MAX-ACCESS read-write
        STATUS     current
        DESCRIPTION
        "The value of prtInputIndex corresponding to the default input
        sub-unit: that is, this object selects the default source of
        input media."
::= { prtGeneralEntry 6 }

prtInputDescription OBJECT-TYPE
        -- In RFC 1759, the SYNTAX was OCTET STRING.  This has been changed
        -- to a TC to better support localization of the object.
        SYNTAX     PrtLocalizedDescriptionStringTC
        MAX-ACCESS read-only
        STATUS     current
        DESCRIPTION
        "A free-form text description of this input sub-unit in the
        localization specified by  prtGeneralCurrentLocalization."
::= { prtInputEntry 18 }

prtInputDimUnit OBJECT-TYPE
        SYNTAX     PrtMediaUnitTC
        MAX-ACCESS read-only
        STATUS     current
        DESCRIPTION
        "The unit of measurement for use calculating and relaying
        dimensional values for this input sub-unit."
::= { prtInputEntry 3 }

prtInputMaxCapacity OBJECT-TYPE
        -- NOTE: In RFC 1759, the range was not defined.
        SYNTAX     Integer32 (-2..2147483647)
        MAX-ACCESS read-write
        STATUS     current
        DESCRIPTION
        "The maximum capacity of the input sub-unit in input sub-unit
        capacity units (PrtCapacityUnitTC).  There is no convention
        associated with the media itself so this value reflects claimed
        capacity.  If this input sub-unit can reliably sense this value,
        the value is sensed by the printer and may not be changed by
        management requests; otherwise, the value may be written (by a
        Remote Control Panel or a Management Application). The value
        (-1) means other and specifically indicates that the sub-unit
        places no restrictions on this parameter.  The value (-2) means
        unknown."
::= { prtInputEntry 9 }

prtInputMediaColor OBJECT-TYPE
        SYNTAX     OCTET STRING (SIZE(0..63))
        MAX-ACCESS read-write
        STATUS     current
        DESCRIPTION
        "The name of the color of the medium associated with
        this input sub-unit using standardized string values.
        NOTE: The above description has been modified from RFC 1759."
        -- The following reference was not included in RFC 1759.
        REFERENCE
        "The PWG Standardized Media Names specification [PWGMEDIA],
        section 4 Media Color Names, contains the recommended values
        for this object.  Implementers may add additional string values.
        The naming conventions in ISO 9070 are recommended in order to
        avoid potential name clashes."
::= { prtInputEntry 22 }

prtInputMediaDimFeedDirChosen OBJECT-TYPE
        -- NOTE: In RFC 1759, the range was not defined.
        SYNTAX     Integer32 (-2..2147483647)
        MAX-ACCESS read-only
        STATUS     current
        DESCRIPTION
        "The printer will act as if media of the chosen dimension (in
        the feed direction) is present in this input source.  Note that
        this value will be used even if the input tray is empty.  Feed
        dimension measurements are taken relative to the feed direction
        associated with that sub-unit and are in input sub-unit
        dimensional units (controlled by prtInputDimUnit, which uses
        PrtMediaUnitTC).  If the printer supports the declared
        dimension,the granted dimension is the same as the declared
        dimension.  If not, the granted dimension is set to the closest
        dimension that the printer supports when the declared dimension
        is set.  The value (-1) means other and specifically indicates
        that this sub-unit places no restriction on this parameter.  The
        value (-2)indicates unknown."
::= { prtInputEntry 6 }

prtInputMediaDimFeedDirDeclared OBJECT-TYPE
        -- NOTE: In RFC 1759, the range was not defined.
        SYNTAX     Integer32 (-2..2147483647)
        MAX-ACCESS read-write
        STATUS     current
        DESCRIPTION
        "This object provides the value of the declared dimension, in
        the feed direction, of the media that is (or, if empty, was or
        will be) in this input sub-unit.  The feed direction is the
        direction in which the media is fed on this sub-unit.  This
        dimension is measured in input sub-unit dimensional units
        (controlled by prtInputDimUnit, which uses PrtMediaUnitTC).  If
        this input sub-unit can reliably sense this value, the value is
        sensed by the printer and may not be changed by management
        requests.  Otherwise, the value may be changed.  The value (-1)
        means other and specifically means that this sub-unit places no
        restriction on this parameter.  The value (-2) indicates
        unknown."
::= { prtInputEntry 4 }

prtInputMediaDimXFeedDirChosen OBJECT-TYPE
        -- NOTE: In RFC 1759, the range was not defined.
        SYNTAX     Integer32 (-2..2147483647)
        MAX-ACCESS read-only
        STATUS     current
        DESCRIPTION
        "The printer will act as if media of the chosen dimension (in
        the cross feed direction) is present in this input source.  Note
        that this value will be used even if the input tray is empty.
        The cross feed direction is ninety degrees relative to the feed
        direction associated with this sub-unit.  This dimension is
        measured in input sub-unit dimensional units (controlled by
        prtInputDimUnit, which uses PrtMediaUnitTC).  If the printer
        supports the declare dimension, the granted dimension is the
        same as the declared dimension.  If not, the granted dimension
        is set to the closest dimension that the printer supports when
        the declared dimension is set.  The value (-1) means other and
        specifically indicates that this sub-unit places no restriction
        on this parameter.  The value (-2) indicates unknown."
::= { prtInputEntry 7 }

prtInputMediaDimXFeedDirDeclared OBJECT-TYPE
        -- NOTE: In RFC 1759, the range was not defined.
        SYNTAX     Integer32 (-2..2147483647)
        MAX-ACCESS read-write
        STATUS     current
        DESCRIPTION
        "This object provides the value of the declared dimension, in
        the cross feed direction, of the media that is (or, if empty,
        was or will be) in this input sub-unit.  The cross  feed
        direction is ninety degrees relative to the feed direction
        associated with this sub-unit.  This dimension is measured in
        input sub-unit dimensional units (controlled by
        prtInputDimUnit,which uses PrtMediaUnitTC).  If this input sub-
        unit can reliably sense this value, the value is sensed by the
        printer and may not be changed by management requests.
        Otherwise, the value may be changed.  The value (-1) means other
        and specifically means that this sub-unit places no restriction
        on this parameter.  The value (-2) indicates unknown."
::= { prtInputEntry 5 }

prtInputMediaFormParts OBJECT-TYPE
        -- NOTE: In RFC 1759, the range was not defined.
        SYNTAX     Integer32 (-2..2147483647)
        MAX-ACCESS read-write
        STATUS     current
        DESCRIPTION
        "The number of parts associated with the medium
        associated with this input sub-unit if the medium is a
        multi-part form.  The value (-1) means other and
        specifically indicates that the device places no
        restrictions on this parameter.  The value (-2) means
        unknown."
::= { prtInputEntry 23 }

prtInputMediaLoadTimeout OBJECT-TYPE
        SYNTAX     Integer32 (-2..2147483647)
        MAX-ACCESS read-write
        STATUS     current
        DESCRIPTION
        "When the printer is not able to print due to a subunit being
        empty or the requested media must be manually loaded, the
        printer will wait for the duration (in seconds) specified by
        this object.  Upon expiration of the time-out, the printer will
        take the action specified by prtInputNextIndex.
        The event which causes the printer to enter the waiting state
        is product specific.  If the printer is not waiting for manually
        fed media, it may switch from an empty subunit to a different
        subunit without waiting for the time-out to expire.
        A value of (-1) implies 'other' or 'infinite' which translates
        to 'wait forever'.  The action which causes printing to continue
        is product specific.  A value of (-2) implies 'unknown'."
::= { prtInputEntry 24 }

prtInputMediaName OBJECT-TYPE
        SYNTAX     OCTET STRING (SIZE(0..63))
        MAX-ACCESS read-write
        STATUS     current
        DESCRIPTION
        "A description of the media contained in this input sub-unit;
        This description is to be used by a client to format and
        Localize a string for display to a human operator.  This
        description is not processed by the printer.  It is used to
        provide information not expressible in terms of the other
        media attributes (e.g., prtInputMediaDimFeedDirChosen,
        prtInputMediaDimXFeedDirChosen, prtInputMediaWeight,
        prtInputMediaType)."
        -- The following reference was not included in RFC 1759.
        REFERENCE
        "The PWG Standardized Media Names specification [PWGMEDIA]
        contains the recommended values for this object.  See also
        RFC 3805 Appendix C,'Media Names', which lists the values
        Of standardized media names defined in ISO/IEC 10175."
::= { prtInputEntry 12 }

prtInputMediaType OBJECT-TYPE
        SYNTAX     OCTET STRING (SIZE(0..63))
        MAX-ACCESS read-write
        STATUS     current
        DESCRIPTION
        "The name of the type of medium associated with this input sub
        unit.  This name need not be processed by the printer; it might
        simply be displayed to an operator.
        NOTE: The above description has been modified from RFC 1759."
        -- The following reference was not included in RFC 1759.
        REFERENCE
        "The PWG Standardized Media Names specification [PWGMEDIA],
        section 3 Media Type Names, contains the recommended values for
        this object.  Implementers may add additional string values.
        The naming conventions in ISO 9070 are recommended in order to
        avoid potential name clashes."
::= { prtInputEntry 21 }

prtInputMediaWeight  OBJECT-TYPE
        -- NOTE: In RFC 1759, the range was not defined.
        SYNTAX     Integer32 (-2..2147483647)
        MAX-ACCESS read-write
        STATUS     current
        DESCRIPTION
        "The weight of the medium associated with this input sub-unit
        in grams / per meter squared.  The value (-2) means unknown."
::= { prtInputEntry 20 }

prtInputModel OBJECT-TYPE
        SYNTAX     OCTET STRING (SIZE(0..63))
        MAX-ACCESS read-only
        STATUS     current
        DESCRIPTION
        "The model name of this input sub-unit."
::= { prtInputEntry 15 }

prtInputName OBJECT-TYPE
        SYNTAX     OCTET STRING (SIZE(0..63))
        MAX-ACCESS read-write
        STATUS     current
        DESCRIPTION
        "The name assigned to this input sub-unit."
::= { prtInputEntry 13 }

prtInputSecurity OBJECT-TYPE
        SYNTAX     PresentOnOff
        MAX-ACCESS read-write
        STATUS     current
        DESCRIPTION
        "Indicates if this input sub-unit has some security associated
        with it."
::= { prtInputEntry 19 }

prtInputSerialNumber OBJECT-TYPE
        SYNTAX     OCTET STRING (SIZE(0..32))
        MAX-ACCESS read-only
        STATUS     current
        DESCRIPTION
        "The serial number assigned to this input sub-unit."
::= { prtInputEntry 17 }

prtInputStatus OBJECT-TYPE
        SYNTAX     PrtSubUnitStatusTC
        MAX-ACCESS read-only
        STATUS     current
        DESCRIPTION
        "The current status of this input sub-unit."
::= { prtInputEntry 11 }

prtInputType OBJECT-TYPE
        -- NOTE: In RFC 1759, the enumeration values were implicitly
        -- defined by this object.
        SYNTAX     PrtInputTypeTC
        MAX-ACCESS read-only
        STATUS     current
        DESCRIPTION
        "The type of technology (discriminated primarily according to
        feeder mechanism type) employed by the input sub-unit.  Note,
        the Input Class provides for a descriptor field to further
        qualify the other choice."
::= { prtInputEntry 2 }

prtInputVendorName OBJECT-TYPE
        SYNTAX     OCTET STRING (SIZE(0..63))
        MAX-ACCESS read-only
        STATUS     current
        DESCRIPTION
        "The vendor name of this input sub-unit."
::= { prtInputEntry 14 }

prtInputVersion OBJECT-TYPE
        SYNTAX     OCTET STRING (SIZE(0..63))
        MAX-ACCESS read-only
        STATUS     current
        DESCRIPTION
        "The version of this input sub-unit."
::= { prtInputEntry 16 }

prtInterpreterDefaultCharSetIn OBJECT-TYPE
        SYNTAX     IANACharset
        MAX-ACCESS read-write
        STATUS     current
        DESCRIPTION
        "The default coded character set for input octets encountered
        outside a context in which the Page Description Language
        established the interpretation of the octets.  (Input octets are
        presented to the interpreter through a path defined in the
        channel group.)"
::= { prtInterpreterEntry 10 }

prtInterpreterDefaultCharSetOut OBJECT-TYPE
        SYNTAX     IANACharset
        MAX-ACCESS read-write
        STATUS     current
        DESCRIPTION
        "The default character set for data coming from this
        interpreter through the printer's output channel (i.e. the
        'backchannel')."
::= { prtInterpreterEntry 11 }

prtInterpreterDefaultOrientation OBJECT-TYPE
        --  NOTE: In RFC 1759, the enumeration values were implicitly
        --  defined by this object.
        SYNTAX     PrtPrintOrientationTC
        MAX-ACCESS read-write
        STATUS     current
        DESCRIPTION
        "The current orientation default for this interpreter.  This
        value may be overridden for a particular job (e.g., by a
        command in the input data stream)."
::= { prtInterpreterEntry 7 }

prtInterpreterDescription OBJECT-TYPE
        -- In RFC 1759, the SYNTAX was OCTET STRING.  This has been changed
        -- to a TC to better support localization of the object.
        SYNTAX     PrtLocalizedDescriptionStringTC
        MAX-ACCESS read-only
        STATUS     current
        DESCRIPTION
        "A string to identify this interpreter in the localization
        specified by prtGeneralCurrentLocalization as opposed to the
        language which is being interpreted.  It is anticipated that
        this string will allow manufacturers to unambiguously identify
        their interpreters."
::= { prtInterpreterEntry 5 }

prtInterpreterFeedAddressability OBJECT-TYPE
        -- NOTE: In RFC 1759, the range was not defined.
        SYNTAX     Integer32 (-2..2147483647)
        MAX-ACCESS read-only
        STATUS     current
        DESCRIPTION
        "The maximum interpreter addressability in the feed
        direction in 10000 prtMarkerAddressabilityUnits (as specified
        by prtMarkerDefaultIndex) for this interpreter.  The
        value (-1) means other and specifically indicates that the
        sub-unit places no restrictions on this parameter.  The value
        (-2) means unknown.
        NOTE: The above description has been modified from RFC 1759
        for clarification."
::= { prtInterpreterEntry 8 }

prtInterpreterLangFamily OBJECT-TYPE
        --  NOTE: In RFC 1759, the enumeration values were implicitly
        --  defined by this object.
        SYNTAX     PrtInterpreterLangFamilyTC
        MAX-ACCESS read-only
        STATUS     current
        DESCRIPTION
        "The family name of a Page Description Language (PDL) or
        control language which this interpreter in the printer can
        interpret or emulate.
        NOTE: The above description has been modified from RFC 1759
        for clarification."
::= { prtInterpreterEntry 2 }

prtInterpreterLangLevel OBJECT-TYPE
        SYNTAX     OCTET STRING (SIZE(0..31))
        MAX-ACCESS read-only
        STATUS     current
        DESCRIPTION
        "The level of the language which this interpreter is
        interpreting or emulating.  This might contain a value like
        '5e'for an interpreter which is emulating level 5e of the PCL
        language.  It might contain '2' for an interpreter which is
        emulating level 2 of the PostScript language.  Similarly it
        might contain '2' for an interpreter which is emulating level 2
        of the HPGL language."
::= { prtInterpreterEntry 3 }

prtInterpreterLangVersion OBJECT-TYPE
        SYNTAX     OCTET STRING (SIZE(0..31))
        MAX-ACCESS read-only
        STATUS     current
        DESCRIPTION
        "The date code or version of the language which this
        interpreter is interpreting or emulating."
::= { prtInterpreterEntry 4 }

prtInterpreterTwoWay OBJECT-TYPE
        --  NOTE: In RFC 1759, the enumeration values were implicitly
        --  defined by this object.
        SYNTAX     PrtInterpreterTwoWayTC
        MAX-ACCESS read-only
        STATUS     current
        DESCRIPTION
        "Indicates whether or not this interpreter returns information
        back to the host."
::= { prtInterpreterEntry 12 }

prtInterpreterVersion OBJECT-TYPE
        SYNTAX     OCTET STRING (SIZE(0..31))
        MAX-ACCESS read-only
        STATUS     current
        DESCRIPTION
        "The date code, version number, or other product specific
        information tied to this interpreter.  This value is associated
        with the interpreter, rather than with the version of the
        language which is being interpreted or emulated."
::= { prtInterpreterEntry 6 }

prtInterpreterXFeedAddressability OBJECT-TYPE
        -- NOTE: In RFC 1759, the range was not defined.
        SYNTAX     Integer32 (-2..2147483647)
        MAX-ACCESS read-only
        STATUS     current
        DESCRIPTION
        "The maximum interpreter addressability in the cross feed
        direction in 10000 prtMarkerAddressabilityUnits (as specified
        by prtMarkerDefaultIndex) for this interpreter.  The
        value (-1) means other and specifically indicates that the
        sub-unit places no restrictions on this parameter.  The value
        (-2) means unknown.
        NOTE: The above description has been modified from RFC 1759
        for clarification."
::= { prtInterpreterEntry 9 }

prtLocalizationCharacterSet OBJECT-TYPE
        SYNTAX     IANACharset
        MAX-ACCESS read-only
        STATUS     current
        DESCRIPTION
        "The coded character set used for this localization."
::= { prtLocalizationEntry 4 }

prtLocalizationCountry OBJECT-TYPE
        -- Note: The size is fixed, was incorrectly 0..2 in RFC 1759.
        SYNTAX     OCTET STRING (SIZE(2))
        MAX-ACCESS read-only
        STATUS     current
        DESCRIPTION
        "A two character country code from ISO 3166, a blank string
        (two space characters) shall indicate that the country is not
        defined.  Examples: US, GB, FR, DE, ..."
::= { prtLocalizationEntry 3 }

prtLocalizationLanguage OBJECT-TYPE
        -- Note: The size is fixed, was incorrectly 0..2 in RFC 1759.
        SYNTAX     OCTET STRING (SIZE(2))
        MAX-ACCESS read-only
        STATUS     current
        DESCRIPTION
        "A two character language code from ISO 639.  Examples en,
        es, fr, de.  NOTE: These examples were shown as upper case in
        RFC 1759 and are now shown as lower case to agree with ISO 639."
::= { prtLocalizationEntry 2 }

prtMarkerAddressabilityFeedDir OBJECT-TYPE
        -- NOTE: In RFC 1759, the range was not defined.
        SYNTAX     Integer32 (-2..2147483647)
        MAX-ACCESS read-only
        STATUS     current
        DESCRIPTION
        "The maximum number of addressable marking positions in the
        feed direction per 10000 units of measure specified by
        prtMarkerAddressabilityUnit.  A value of (-1) implies 'other'
        or 'infinite' while a value of (-2) implies 'unknown'.
        NOTE: The above description has been modified from RFC 1759
        for clarification."
::= { prtMarkerEntry 9 }

prtMarkerAddressabilityUnit OBJECT-TYPE
        --  NOTE: In RFC 1759, the enumeration values were implicitly
        --  defined by this object.
        SYNTAX     PrtMarkerAddressabilityUnitTC
        MAX-ACCESS read-only
        STATUS     current
        DESCRIPTION
        "The unit of measure of distances, as applied to the marker's
        resolution.
        NOTE: The above description has been modified from RFC 1759
        for clarification."
::= { prtMarkerEntry 8 }

prtMarkerAddressabilityXFeedDir OBJECT-TYPE
        -- NOTE: In RFC 1759, the range was not defined.
        SYNTAX     Integer32 (-2..2147483647)
        MAX-ACCESS read-only
        STATUS     current
        DESCRIPTION
        "The maximum number of addressable marking positions in the
        cross feed direction in 10000 units of measure specified by
        prtMarkerAddressabilityUnit.  A value of (-1) implies 'other'
        or 'infinite' while a value of (-2) implies 'unknown'.
        NOTE: The above description has been modified from RFC 1759
        for clarification."
::= { prtMarkerEntry 10 }

prtMarkerColorantMarkerIndex OBJECT-TYPE
        SYNTAX     Integer32 (0..65535)
        MAX-ACCESS read-only
        STATUS     current
        DESCRIPTION
        "The value of prtMarkerIndex corresponding to the marker sub
        unit with which this colorant entry is associated."
::= { prtMarkerColorantEntry 2 }

prtMarkerColorantRole OBJECT-TYPE
        --  NOTE: In RFC 1759, the enumeration values were implicitly
        --  defined by this object.
        SYNTAX     PrtMarkerColorantRoleTC
        MAX-ACCESS read-only
        STATUS     current
        DESCRIPTION
        "The role played by this colorant."
::= { prtMarkerColorantEntry 3 }

prtMarkerColorantTonality OBJECT-TYPE
        -- NOTE: In RFC 1759, the range was not defined.
        SYNTAX     Integer32 (2..2147483647)
        MAX-ACCESS read-only
        STATUS     current
        DESCRIPTION
        "The distinct levels of tonality realizable by a marking sub
        unit when using this colorant.  This value does not include the
        number of levels of tonal difference that an interpreter can
        obtain by techniques such as half toning.  This value must be at
        least 2."
::= { prtMarkerColorantEntry 5 }

prtMarkerColorantValue OBJECT-TYPE
        -- NOTE: The string length range has been increased from RFC 1759.
        SYNTAX     OCTET STRING (SIZE(0..255))
        MAX-ACCESS read-only
        STATUS     current
        DESCRIPTION
        "The name of the color of this colorant using standardized
        string names from ISO 10175 (DPA) and ISO 10180 (SPDL) such as:
        other
        unknown
        white
        red
        green
        blue
        cyan
        magenta
        yellow
        black
        Implementers may add additional string values.  The naming
        conventions in ISO 9070 are recommended in order to avoid
        potential name clashes"
::= { prtMarkerColorantEntry 4 }

prtMarkerCounterUnit OBJECT-TYPE
        --  NOTE: In RFC 1759, the enumeration values were implicitly
        --  defined by this object.
        SYNTAX     PrtMarkerCounterUnitTC
        MAX-ACCESS read-only
        STATUS     current
        DESCRIPTION
        "The unit that will be used by the printer when reporting
        counter values for this marking sub-unit.  The time units of
        measure are provided for a device like a strip recorder that
        does not or cannot track the physical dimensions of the media
        and does not use characters, lines or sheets."
::= { prtMarkerEntry 3 }

prtMarkerDefaultIndex OBJECT-TYPE
        SYNTAX     Integer32 (1..65535)
        MAX-ACCESS read-write
        STATUS     current
        DESCRIPTION
        "The value of prtMarkerIndex corresponding to the
        default marker sub-unit; that is, this object selects the
        default marker."
::= { prtGeneralEntry 8 }

prtMarkerEastMargin OBJECT-TYPE
        -- NOTE: In RFC 1759, the range was not defined.
        SYNTAX     Integer32 (-2..2147483647)
        MAX-ACCESS read-only
        STATUS     current
        DESCRIPTION
        "The margin from the East edge (see prtMarkerNorthMargin) of
        the medium in units identified by prtMarkerAddressabilityUnit.
        Printing within the area bounded by all four margins is
        guaranteed for all interpreters.  The value (-2) means unknown."
::= { prtMarkerEntry 14 }

prtMarkerLifeCount OBJECT-TYPE
        SYNTAX     Counter32
        MAX-ACCESS read-only
        STATUS     current
        DESCRIPTION
        "The count of the number of units of measure counted during the
        life of printer using units of measure as specified by
        prtMarkerCounterUnit.
        Note: This object should be implemented as a persistent object
        with a reliable value throughout the lifetime of the printer."
::= { prtMarkerEntry 4 }

prtMarkerMarkTech OBJECT-TYPE
        --  NOTE: In RFC 1759, the enumeration values were implicitly
        --  defined by this object.
        SYNTAX     PrtMarkerMarkTechTC
        MAX-ACCESS read-only
        STATUS     current
        DESCRIPTION
        "The type of marking technology used for this marking
        sub-unit."
::= { prtMarkerEntry 2 }

prtMarkerNorthMargin OBJECT-TYPE
        -- NOTE: In RFC 1759, the range was not defined.
        SYNTAX     Integer32 (-2..2147483647)
        MAX-ACCESS read-only
        STATUS     current
        DESCRIPTION
        "The margin, in units identified by prtMarkerAddressabilityUnit,
        from the leading edge of the medium as the medium flows through
        the marking engine with the side to be imaged facing the
        observer.  The leading edge is the North edge and the other
        edges are defined by the normal compass layout of  directions
        with the compass facing the observer.  Printing within the area
        bounded by all four margins is guaranteed for all interpreters.
        The value (-2) means unknown."
::= { prtMarkerEntry 11 }

prtMarkerPowerOnCount OBJECT-TYPE
        SYNTAX     Counter32
        MAX-ACCESS read-only
        STATUS     current
        DESCRIPTION
        "The count of the number of units of measure counted since the
        equipment was most recently powered on using units of measure
        as specified by prtMarkerCounterUnit."
::= { prtMarkerEntry 5 }

prtMarkerProcessColorants OBJECT-TYPE
        SYNTAX     Integer32 (0..65535)
        MAX-ACCESS read-only
        STATUS     current
        DESCRIPTION
        "The number of process colors supported by this marker.  A
        process color of 1 implies monochrome.  The value of this
        object and prtMarkerSpotColorants cannot both be 0.  The value
        of prtMarkerProcessColorants must be 0 or greater.
        NOTE: The above description has been modified from RFC 1759
        for clarification."
::= { prtMarkerEntry 6 }

prtMarkerSouthMargin OBJECT-TYPE
        -- NOTE: In RFC 1759, the range was not defined.
        SYNTAX     Integer32 (-2..2147483647)
        MAX-ACCESS read-only
        STATUS     current
        DESCRIPTION
        "The margin from the South edge  (see prtMarkerNorthMargin) of
        the medium in units identified by prtMarkerAddressabilityUnit.
        Printing within the area bounded by all four margins  is
        guaranteed for all interpreters.  The value (-2) means unknown."
::= { prtMarkerEntry 12 }

prtMarkerSpotColorants OBJECT-TYPE
        SYNTAX     Integer32 (0..65535)
        MAX-ACCESS read-only
        STATUS     current
        DESCRIPTION
        "The number of spot colors supported by this marker.  The value
        of this object and prtMarkerProcessColorants cannot both be 0.
        Must be 0 or greater.
        NOTE: The above description has been modified from RFC 1759
        for clarification."
::= { prtMarkerEntry 7 }

prtMarkerStatus OBJECT-TYPE
        SYNTAX     PrtSubUnitStatusTC
        MAX-ACCESS read-only
        STATUS     current
        DESCRIPTION
        "The current status of this marker sub-unit."
::= { prtMarkerEntry 15 }

prtMarkerSuppliesClass OBJECT-TYPE
        --  NOTE: In RFC 1759, the enumeration values were implicitly
        --  defined by this object.
        SYNTAX     PrtMarkerSuppliesClassTC
        MAX-ACCESS read-only
        STATUS     current
        DESCRIPTION
        "Indicates whether this supply entity represents a supply that
        is consumed or a receptacle that is filled.
        NOTE: The above description has been modified from RFC 1759
        for clarification."
::= { prtMarkerSuppliesEntry 4 }

prtMarkerSuppliesColorantIndex OBJECT-TYPE
        SYNTAX     Integer32 (0..65535)
        MAX-ACCESS read-only
        STATUS     current
        DESCRIPTION
        "The value of prtMarkerColorantIndex corresponding to the
        colorant with which this marker supply sub-unit is associated.
        This value shall be 0 if there is no colorant table or if this
        supply does not depend on a single specified colorant.
        NOTE: The above description has been modified from RFC 1759
        for clarification."
::= { prtMarkerSuppliesEntry 3 }

prtMarkerSuppliesDescription OBJECT-TYPE
        -- In RFC 1759, the SYNTAX was OCTET STRING.  This has been changed
        -- to a TC to better support localization of the object.
        SYNTAX     PrtLocalizedDescriptionStringTC
        MAX-ACCESS read-only
        STATUS     current
        DESCRIPTION
        "The description of this supply container/receptacle in the
        localization specified by prtGeneralCurrentLocalization."
::= { prtMarkerSuppliesEntry 6 }

prtMarkerSuppliesLevel OBJECT-TYPE
        -- NOTE: In RFC 1759, the range was not defined.
        SYNTAX     Integer32 (-3..2147483647)
        MAX-ACCESS read-write
        STATUS     current
        DESCRIPTION
        "The current level if this supply is a container; the remaining
        space if this supply is a receptacle.  If this supply
        container/receptacle can reliably sense this value, the value
        is reported by the printer and is read-only; otherwise, the
        value may be written (by a Remote Control Panel or a Management
        Application).  The value (-1) means other and specifically
        indicates that the sub-unit places no restrictions on this
        parameter.  The value (-2) means unknown.  A value of (-3) means
        that the printer knows that there is some supply/remaining
        space, respectively."
::= { prtMarkerSuppliesEntry 9 }

prtMarkerSuppliesMarkerIndex OBJECT-TYPE
        SYNTAX     Integer32 (0..65535)
        MAX-ACCESS read-only
        STATUS     current
        DESCRIPTION
        "The value of prtMarkerIndex corresponding to the marking sub
        unit with which this marker supply sub-unit is associated."
::= { prtMarkerSuppliesEntry 2 }

prtMarkerSuppliesMaxCapacity OBJECT-TYPE
        -- NOTE: In RFC 1759, the range was not defined.
        SYNTAX     Integer32 (-2..2147483647)
        MAX-ACCESS read-write
        STATUS     current
        DESCRIPTION
        "The maximum capacity of this supply container/receptacle
        expressed in prtMarkerSuppliesSupplyUnit.  If this supply
        container/receptacle can reliably sense this value, the value
        is reported by the printer and is read-only; otherwise, the
        value may be written (by a Remote Control Panel or a Management
        Application).  The value (-1) means other and specifically
        indicates that the sub-unit places no restrictions on this
        parameter.  The value (-2) means unknown."
::= { prtMarkerSuppliesEntry 8 }

prtMarkerSuppliesSupplyUnit OBJECT-TYPE
        --  NOTE: In RFC 1759, the enumeration values were implicitly
        --  defined by this object.
        SYNTAX     PrtMarkerSuppliesSupplyUnitTC
        MAX-ACCESS read-only
        STATUS     current
        DESCRIPTION
        "Unit of measure of this marker supply container/receptacle.
        NOTE: The above description has been modified from RFC 1759
        for clarification."
::= { prtMarkerSuppliesEntry 7 }

prtMarkerSuppliesType OBJECT-TYPE
        --  NOTE: In RFC 1759, the enumeration values were implicitly
        --  defined by this object.
        SYNTAX     PrtMarkerSuppliesTypeTC
        MAX-ACCESS read-only
        STATUS     current
        DESCRIPTION
        "The type of this supply."
::= { prtMarkerSuppliesEntry 5 }

prtMarkerWestMargin OBJECT-TYPE
        -- NOTE: In RFC 1759, the range was not defined.
        SYNTAX     Integer32 (-2..2147483647)
        MAX-ACCESS read-only
        STATUS     current
        DESCRIPTION
        "The margin from the West edge (see prtMarkerNorthMargin) of
        the medium in units identified by prtMarkerAddressabilityUnit.
        Printing within the area bounded by all four margins is
        guaranteed for all interpreters.  The value (-2) means unknown."
::= { prtMarkerEntry 13 }

prtMediaPathDefaultIndex OBJECT-TYPE
        SYNTAX     Integer32 (1..65535)
        MAX-ACCESS read-write
        STATUS     current
        DESCRIPTION
        "The value of prtMediaPathIndex corresponding to
        the default media path; that is, the selection of the
        default media path."
::= { prtGeneralEntry 9 }

prtMediaPathDescription OBJECT-TYPE
        -- In RFC 1759, the SYNTAX was OCTET STRING.  This has been changed
        -- to a TC to better support localization of the object.
        SYNTAX     PrtLocalizedDescriptionStringTC
        MAX-ACCESS read-only
        STATUS     current
        DESCRIPTION
        "The manufacturer-provided description of this media path in
        the localization specified by prtGeneralCurrentLocalization."
::= { prtMediaPathEntry 10 }

prtMediaPathMaxMediaFeedDir OBJECT-TYPE
        -- NOTE: In RFC 1759, the range was not defined.
        SYNTAX     Integer32 (-2..2147483647)
        MAX-ACCESS read-only
        STATUS     current
        DESCRIPTION
        "The maximum physical media size in the feed direction of this
        media path expressed in units of measure specified by
        PrtMediaPathMediaSizeUnit.  A value of (-1) implies 'unlimited'
        a value of (-2) implies 'unknown'.
        NOTE: The above description has been modified from RFC 1759
        for clarification."
::= { prtMediaPathEntry 5 }

prtMediaPathMaxMediaXFeedDir OBJECT-TYPE
        -- NOTE: In RFC 1759, the range was not defined.
        SYNTAX     Integer32 (-2..2147483647)
        MAX-ACCESS read-only
        STATUS     current
        DESCRIPTION
        "The maximum physical media size across the feed direction of
        this media path expressed in units of measure specified by
        prtMediaPathMediaSizeUnit.  A value of (-2) implies 'unknown'.
        NOTE: The above description has been modified from RFC 1759
        for clarification."
::= { prtMediaPathEntry 6 }

prtMediaPathMaxSpeed OBJECT-TYPE
        -- NOTE: In RFC 1759, the range was not defined.
        SYNTAX     Integer32 (-2..2147483647)
        MAX-ACCESS read-only
        STATUS     current
        DESCRIPTION
        "The maximum printing speed of this media path expressed in
        prtMediaPathMaxSpeedUnit's.  A value of (-1) implies 'other'."
::= { prtMediaPathEntry 4 }

prtMediaPathMaxSpeedPrintUnit OBJECT-TYPE
        --  NOTE: In RFC 1759, the enumeration values were implicitly
        --  defined by this object.
        SYNTAX PrtMediaPathMaxSpeedPrintUnitTC
        MAX-ACCESS read-only
        STATUS     current
        DESCRIPTION
        "The unit of measure used in specifying the speed of all media
        paths in the printer."
::= { prtMediaPathEntry 2 }

prtMediaPathMediaSizeUnit OBJECT-TYPE
        SYNTAX     PrtMediaUnitTC
        MAX-ACCESS read-only
        STATUS     current
        DESCRIPTION
        "The units of measure of media size for use in calculating and
        relaying dimensional values for all media paths in the
        printer."
::= { prtMediaPathEntry 3 }

prtMediaPathMinMediaFeedDir OBJECT-TYPE
        -- NOTE: In RFC 1759, the range was not defined.
        SYNTAX     Integer32 (-2..2147483647)
        MAX-ACCESS read-only
        STATUS     current
        DESCRIPTION
        "The minimum physical media size in the feed direction of this
        media path expressed in units of measure specified by
        prtMediaPathMediaSizeUnit.  A value of (-2) implies 'unknown'.
        NOTE: The above description has been modified from RFC 1759
        for clarification."
::= { prtMediaPathEntry 7 }

prtMediaPathMinMediaXFeedDir OBJECT-TYPE
        -- NOTE: In RFC 1759, the range was not defined.
        SYNTAX     Integer32 (-2..2147483647)
        MAX-ACCESS read-only
        STATUS     current
        DESCRIPTION
        "The minimum physical media size across the feed direction of
        this media path expressed in units of measure specified by
        prtMediaPathMediaSizeUnit.  A value of (-2) implies 'unknown'.
        NOTE: The above description has been modified from RFC 1759
        for clarification."
::= { prtMediaPathEntry 8 }

prtMediaPathStatus OBJECT-TYPE
        SYNTAX     PrtSubUnitStatusTC
        MAX-ACCESS read-only
        STATUS     current
        DESCRIPTION
        "The current status of this media path."
::= { prtMediaPathEntry 11 }

prtMediaPathType OBJECT-TYPE
        --  NOTE: In RFC 1759, the enumeration values were implicitly
        --  defined by this object.
        SYNTAX     PrtMediaPathTypeTC
        MAX-ACCESS read-only
        STATUS     current
        DESCRIPTION
        "The type of the media path for this media path."
::= { prtMediaPathEntry 9 }

prtOutputBursting OBJECT-TYPE
        SYNTAX     PresentOnOff
        MAX-ACCESS read-write
        STATUS     current
        DESCRIPTION
        "This object indicates that the outputting sub-unit supports
        bursting, and if so, whether the feature is enabled.  Bursting
        is the process by which continuous media is separated into
        individual sheets, typically by bursting along pre-formed
        perforations."
::= { prtOutputEntry 21 }

prtOutputCapacityUnit OBJECT-TYPE
        SYNTAX     PrtCapacityUnitTC
        MAX-ACCESS read-only
        STATUS     current
        DESCRIPTION
        "The unit of measurement for use in calculating and relaying
        capacity values for this output sub-unit."
::= { prtOutputEntry 3 }

prtOutputDecollating OBJECT-TYPE
        SYNTAX     PresentOnOff
        MAX-ACCESS read-write
        STATUS     current
        DESCRIPTION
        "This object indicates that the output supports decollating,
        and if so, whether the feature is enabled.  Decollating is the
        process by which the individual parts within a multi-part form
        are separated and sorted into separate stacks for each part."
::= { prtOutputEntry 22 }

prtOutputDefaultIndex OBJECT-TYPE
        --  A range has been added to the SYNTAX clause that was not in
        --  RFC 1759.  Although this violates SNMP compatibility rules,
        --  it provides a more reasonable guide for SNMP managers.
        SYNTAX     Integer32 (1..65535)
        MAX-ACCESS read-write
        STATUS     current
        DESCRIPTION
        "The value of prtOutputIndex corresponding to the default
        output sub-unit; that is, this object selects the default
        output destination."
::= { prtGeneralEntry 7 }

prtOutputDescription OBJECT-TYPE
        -- In RFC 1759, the SYNTAX was OCTET STRING.  This has been changed
        -- to a TC to better support localization of the object.
        SYNTAX     PrtLocalizedDescriptionStringTC
        MAX-ACCESS read-only
        STATUS     current
        DESCRIPTION
        "A free-form text description of this output sub-unit in the
        localization specified by prtGeneralCurrentLocalization."
::= { prtOutputEntry 12 }

prtOutputDimUnit OBJECT-TYPE
        SYNTAX     PrtMediaUnitTC
        MAX-ACCESS read-only
        STATUS     current
        DESCRIPTION
        "The unit of measurement for use in calculating and relaying
        dimensional values for this output sub-unit."
::= { prtOutputEntry 14 }

prtOutputMaxCapacity OBJECT-TYPE
        -- NOTE: In RFC 1759, the range was not defined.
        SYNTAX     Integer32 (-2..2147483647)
        MAX-ACCESS read-write
        STATUS     current
        DESCRIPTION
        "The maximum capacity of this output sub-unit in output sub-
        unit capacity units (PrtCapacityUnitTC).  There is no convention
        associated with the media itself so this value essentially
        reflects claimed capacity.  If this output sub-unit can reliably
        sense this value, the value is sensed by the printer and may
        not be changed by management requests; otherwise, the value may
        be written (by a Remote Control Panel or a Management
        Application).  The value (-1) means other and specifically
        indicates that the sub-unit places no restrictions on this
        parameter.  The value (-2) means unknown."
::= { prtOutputEntry 4 }

prtOutputMaxDimFeedDir OBJECT-TYPE
        -- NOTE: In RFC 1759, the range was not defined.
        SYNTAX     Integer32 (-2..2147483647)
        MAX-ACCESS read-write
        STATUS     current
        DESCRIPTION
        "The maximum dimensions supported by this output sub-unit
        for measurements taken parallel relative to the feed
        direction associated with that sub-unit in output
        sub-unit dimensional units (controlled by prtOutputDimUnit,
        which uses PrtMediaUnitTC).  If this output sub-unit can
        reliably sense this value, the value is sensed by the printer
        and may not be changed with management protocol operations.
        The value (-1) means other and specifically indicates that the
        sub-unit places no restrictions on this parameter.  The value
        (-2) means unknown.
        NOTE: The above description has been modified from RFC 1759
        for clarification and to explain the purpose of (-1) and (-2)."
::= { prtOutputEntry 15 }

prtOutputMaxDimXFeedDir OBJECT-TYPE
        -- NOTE: In RFC 1759, the range was not defined.
        SYNTAX     Integer32 (-2..2147483647)
        MAX-ACCESS read-write
        STATUS     current
        DESCRIPTION
        "The maximum dimensions supported by this output sub-unit
        for measurements taken ninety degrees relative to the
        feed direction associated with that sub-unit in output
        sub-unit dimensional units (controlled by prtOutputDimUnit,
        which uses PrtMediaUnitTC).  If this output sub-unit can
        reliably sense this value, the value is sensed by the printer
        and may not be changed with management protocol operations.
        The value (-1) means other and specifically indicates that the
        sub-unit places no restrictions on this parameter.  The value
        (-2) means unknown.
        NOTE: The above description has been modified from RFC 1759
        for clarification and to explain the purpose of (-1) and (-2)."
::= { prtOutputEntry 16 }

prtOutputMinDimFeedDir OBJECT-TYPE
        -- NOTE: In RFC 1759, the range was not defined.
        SYNTAX     Integer32 (-2..2147483647)
        MAX-ACCESS read-write
        STATUS     current
        DESCRIPTION
        "The minimum dimensions supported by this output sub-unit
        for measurements taken parallel relative to the feed
        direction associated with that sub-unit in output
        sub-unit dimensional units (controlled by prtOutputDimUnit,
        which uses PrtMediaUnitTC).  If this output sub-unit can
        reliably sense this value, the value is sensed by the printer
        and may not be changed with management protocol operations.
        The value (-1) means other and specifically indicates that the
        sub-unit places no restrictions on this parameter.  The value
        (-2) means unknown.
        NOTE: The above description has been modified from RFC 1759
        for clarification and to explain the purpose of (-1) and (-2)."
::= { prtOutputEntry 17 }

prtOutputMinDimXFeedDir OBJECT-TYPE
        -- NOTE: In RFC 1759, the range was not defined.
        SYNTAX     Integer32 (-2..2147483647)
        MAX-ACCESS read-write
        STATUS     current
        DESCRIPTION
        "The minimum dimensions supported by this output sub-unit
        for measurements taken ninety degrees relative to the
        feed direction associated with that sub-unit in output
        sub-unit dimensional units (controlled by prtOutputDimUnit,
        which uses PrtMediaUnitTC).  If this output sub-unit can
        reliably sense this value, the value is sensed by the printer
        and may not be changed with management protocol operations.
        The value (-1) means other and specifically indicates that the
        sub-unit places no restrictions on this parameter.  The value
        (-2) means unknown.
        NOTE: The above description has been modified from RFC 1759
        for clarification and to explain the purpose of (-1) and (-2)."
::= { prtOutputEntry 18 }

prtOutputModel OBJECT-TYPE
        SYNTAX     OCTET STRING (SIZE(0..63))
        MAX-ACCESS read-only
        STATUS     current
        DESCRIPTION
        "The model name assigned to this output sub-unit.
        NOTE: The above description has been modified from RFC 1759
        for clarification."
::= { prtOutputEntry 9 }

prtOutputName OBJECT-TYPE
        SYNTAX     OCTET STRING (SIZE(0..63))
        MAX-ACCESS read-write
        STATUS     current
        DESCRIPTION
        "The name assigned to this output sub-unit."
::= { prtOutputEntry 7 }

prtOutputOffsetStacking OBJECT-TYPE
        SYNTAX     PresentOnOff
        MAX-ACCESS read-write
        STATUS     current
        DESCRIPTION
        "This object indicates that the output supports offset
        stacking,and if so, whether the feature is enabled.  See RFC
        3805 Appendix A, Glossary Of Terms,  for how Offset Stacking is
        defined by this document.
        NOTE: The above description has been modified from RFC 1759
        for clarification."
::= { prtOutputEntry 24 }

prtOutputPageCollated OBJECT-TYPE
        SYNTAX     PresentOnOff
        MAX-ACCESS read-write
        STATUS     current
        DESCRIPTION
        "This object indicates that the output sub-unit supports page
        collation, and if so, whether the feature is enabled.  See RFC
        3805 Appendix A, Glossary Of Terms, for definition of how this
        document defines collation.
        NOTE: The above description has been modified from RFC 1759
        for clarification."
::= { prtOutputEntry 23 }

prtOutputPageDeliveryOrientation OBJECT-TYPE
        --  NOTE: In RFC 1759, the enumeration values were implicitly
        --  defined by this object.
        SYNTAX     PrtOutputPageDeliveryOrientationTC
        MAX-ACCESS read-write
        STATUS     current
        DESCRIPTION
        "The reading surface that will be 'up' when pages are
        delivered to the associated output sub-unit.  Values are
        faceUp and faceDown.  (Note: interpretation of these
        values is in general context-dependent based on locale;
        presentation of these values to an end-user should be
        normalized to the expectations of the user)."
::= { prtOutputEntry 20 }

prtOutputRemainingCapacity OBJECT-TYPE
        -- NOTE: In RFC 1759, the range was not defined.
        SYNTAX     Integer32 (-3..2147483647)
        MAX-ACCESS read-write
        STATUS     current
        DESCRIPTION
        "The remaining capacity of the possible output sub-unit
        capacity in output sub-unit capacity units
        (PrtCapacityUnitTC)of this output sub-unit.  If this output sub-
        unit can reliably sense this value, the value is sensed by the
        printer and may not be modified by management requests;
        otherwise, the value may be written (by a Remote Control Panel
        or a Management Application).  The value (-1) means other and
        specifically indicates that the sub-unit places no restrictions
        on this parameter.  The value (-2) means unknown.  The value
        (-3) means that the printer knows that there remains capacity
        for at least one unit."
::= { prtOutputEntry 5 }

prtOutputSecurity OBJECT-TYPE
        SYNTAX     PresentOnOff
        MAX-ACCESS read-write
        STATUS     current
        DESCRIPTION
        "Indicates if this output sub-unit has some security associated
        with it and if that security is enabled or not."
::= { prtOutputEntry 13 }

prtOutputSerialNumber OBJECT-TYPE
        SYNTAX     OCTET STRING (SIZE(0..63))
        MAX-ACCESS read-only
        STATUS     current
        DESCRIPTION
        "The serial number assigned to this output sub-unit."
::= { prtOutputEntry 11 }

prtOutputStackingOrder OBJECT-TYPE
        --  NOTE: In RFC 1759, the enumeration values were implicitly
        --  defined by this object.
        SYNTAX     PrtOutputStackingOrderTC
        MAX-ACCESS read-write
        STATUS     current
        DESCRIPTION
        "The current state of the stacking order for the
        associated output sub-unit. 'FirstToLast' means
        that as pages are output the front of the next page is
        placed against the back of the previous page.
        'LasttoFirst' means that as pages are output the back
        of the next page is placed against the front of the
        previous page."
::= { prtOutputEntry 19 }

prtOutputStatus OBJECT-TYPE
        SYNTAX     PrtSubUnitStatusTC
        MAX-ACCESS read-only
        STATUS     current
        DESCRIPTION
        "The current status of this output sub-unit."
::= { prtOutputEntry 6 }

prtOutputType OBJECT-TYPE
        -- NOTE: In RFC 1759, the enumeration values were implicitly defined
        -- by this object.
        SYNTAX     PrtOutputTypeTC
        MAX-ACCESS read-only
        STATUS     current
        DESCRIPTION
        "The type of technology supported by this output sub-unit."
::= { prtOutputEntry 2 }

prtOutputVendorName OBJECT-TYPE
        SYNTAX     OCTET STRING (SIZE(0..63))
        MAX-ACCESS read-only
        STATUS     current
        DESCRIPTION
        "The vendor name of this output sub-unit."
::= { prtOutputEntry 8 }

prtOutputVersion OBJECT-TYPE
        SYNTAX     OCTET STRING (SIZE(0..63))
        MAX-ACCESS read-only
        STATUS     current
        DESCRIPTION
        "The version of this output sub-unit."
::= { prtOutputEntry 10 }

scan-to-folder-count OBJECT-TYPE
        SYNTAX      INTEGER(0..9999999)
        ACCESS      read-only
        STATUS      optional
        DESCRIPTION "The number of scan-to-folder scan jobs.
        Additional information:
        The number of scan-to-folder scan jobs."
::= { settings-scanner 89 }

scanner-accessory-adf-sheet-count OBJECT-TYPE
        SYNTAX      INTEGER(0..2147483647)
        ACCESS      read-only
        STATUS      optional
        DESCRIPTION "Total number of sheets that have been fed through the Automatic
        Document Feed (ADF) accessory.
        Additional information:
        The Automatic Document Feed (ADF) count is
        incremented each time a sheet feeds through the
        ADF.
        The value will be updated at the end of every
        scan job. "
::= { settings-scanner 20 }

scanner-accessory-copy-job-scan-count OBJECT-TYPE
        SYNTAX      INTEGER
        ACCESS      read-only
        STATUS      optional
        DESCRIPTION "This relates to the number of pages scanned for copying. This
        item is incremented by 2 for each sheet scanned through the ADF
        in 2-sided scan mode, and it is incremented by 1 for flatbed
        scans. Scanning for testing and calibration purposes are NOT TO
        BE INCLUDED in this count.
        Additional information:
        The value will be updated at the end of every
        scan job. "
::= { settings-scanner 61 }

scanner-accessory-flatbed-scan-count OBJECT-TYPE
        SYNTAX      INTEGER(0..2147483647)
        ACCESS      read-only
        STATUS      optional
        DESCRIPTION "Total number of scans performed by a flatbed scanner
        accessory.
        Additional information:
        The count is only incremented when a sheet is
        scanned on the FLATBED.
        The return value of this object will reset
        to the lower multiple of 10 at a power cycle.
        The value will be updated at the end of every
        scan job. "
::= { settings-scanner 21 }

scanner-accessory-send-job-scan-count OBJECT-TYPE
        SYNTAX      INTEGER
        ACCESS      read-only
        STATUS      optional
        DESCRIPTION "This relates to the number of pages scanned for fax/send. This
        item is incremented by 2 for each sheet scanned through the ADF
        in 2-sided scan mode, and it is incremented by 1 for flatbed
        scans. Scanning for testing and calibration purposes are NOT TO
        BE INCLUDED in this count.
        Additional information:
        The value will be updated at the end of every
        scan job. "
::= { settings-scanner 62 }

scanner-accessory-total-copy-color-pages-printed OBJECT-TYPE
        SYNTAX  INTEGER
        ACCESS  read-only
        STATUS  optional
        DESCRIPTION
        "This relates to the number of copy color pages printed on a
        device.The output sheet that is duplexed (made 2-sided) should
        be counted as 2 pages."
::= { settings-scanner 123 }

scanner-accessory-total-copy-mono-pages-printed OBJECT-TYPE
        SYNTAX  INTEGER
        ACCESS  read-only
        STATUS  optional
        DESCRIPTION
        "This relates to the number of copy mono pages printed on a
        device.The output sheet that is duplexed (made 2-sided) should
        be counted as 2 pages."
::= { settings-scanner 122 }

scanner-accessory-total-copy-pages-printed OBJECT-TYPE
        SYNTAX      INTEGER
        ACCESS      read-only
        STATUS      optional
        DESCRIPTION "This relates to the number of copy pages printed on a device.
        The output sheet that is duplexed (made 2- sided) should be
        counted as 2 pages."
::= { settings-scanner 63 }

serial-number OBJECT-TYPE
        SYNTAX  DisplayString (SIZE(0..10))
        ACCESS  read-only
        STATUS  optional
        DESCRIPTION
        "Identifies the serial number for the device. If the
        SERIAL-NUMBER object is set by the user, then setting the
        object does not need to be protected. If the SERIAL-NUMBER
        object is set at the factory, then the SERVICE-PASSWORD object
        must be set correctly before the SERIAL-NUMBER object is
        writable. If this is a writable object, the POS should indicate
        the maximum supported string length. If possible, encode the
        serial number in a symbol set (like Roman-8) that matches the
        ASCII character set and limit the characters used to ASCII
        characters."
::= { id 3 }

setCommunityName	OBJECT-TYPE
        SYNTAX			OCTET STRING  ( SIZE ( 0 .. 255  ) )
        MAX-ACCESS		read-write
        STATUS			current
        DESCRIPTION
        "This object controls access of snmp read-write requests.  Factory
        default configuration provides authentication of incoming packets
        with community names: internal and public.  This object overrides the
        factory default settings so that the factory default setttings no longer
        work. This object returns SET or NOT_SET."
::=  {  community  1  }

sleep-mode OBJECT-TYPE
        SYNTAX  INTEGER {
        eFalse(1),
        eTrue(2)
        }
        ACCESS  read-write
        STATUS  optional
        DESCRIPTION
        "Returns eTrue if the device is in energy saving sleep mode,
        otherwise returns eFalse. Setting SLEEP-MODE to eFalse causes
        the device to wake up, if it is in sleep mode. Setting
        SLEEP-MODE to eTrue causes the device to go into sleep mode."
::= { settings-system 2 }

snmpEnableAuthenTraps OBJECT-TYPE
        SYNTAX  INTEGER { enabled(1), disabled(2) }
        ACCESS  read-write
        STATUS  mandatory
        DESCRIPTION
        "Indicates whether the SNMP agent process is
        permitted to generate authentication-failure
        traps.  The value of this object overrides any
        configuration information; as such, it provides a
        means whereby all authentication-failure traps may
        be disabled.
        Note that it is strongly recommended that this
        object be stored in non-volatile memory so that it
        remains constant between re-initializations of the
        network management system."
::= { snmp 30 }

snmpEngineBoots  OBJECT-TYPE
        SYNTAX       INTEGER (1..2147483647)
        MAX-ACCESS   read-only
        STATUS       current
        DESCRIPTION "The number of times that the SNMP engine has
        (re-)initialized itself since snmpEngineID
        was last configured.
        "
::= { snmpEngine 2 }

snmpEngineID     OBJECT-TYPE
        SYNTAX       SnmpEngineID
        MAX-ACCESS   read-only
        STATUS       current
        DESCRIPTION "An SNMP engine's administratively-unique identifier.
        This information SHOULD be stored in non-volatile
        storage so that it remains constant across
        re-initializations of the SNMP engine.
        "
::= { snmpEngine 1 }

snmpEngineMaxMessageSize OBJECT-TYPE
        SYNTAX       INTEGER (484..2147483647)
        MAX-ACCESS   read-only
        STATUS       current
        DESCRIPTION "The maximum length in octets of an SNMP message
        which this SNMP engine can send or receive and
        process, determined as the minimum of the maximum
        message size values supported among all of the
        transports available to and supported by the engine.
        "
::= { snmpEngine 4 }

snmpEngineTime   OBJECT-TYPE
        SYNTAX       INTEGER (0..2147483647)
        UNITS        "seconds"
        MAX-ACCESS   read-only
        STATUS       current
        DESCRIPTION "The number of seconds since the value of
        the snmpEngineBoots object last changed.
        When incrementing this object's value would
        cause it to exceed its maximum,
        snmpEngineBoots is incremented as if a
        re-initialization had occurred, and this
        object's value consequently reverts to zero.
        "
::= { snmpEngine 3 }

snmpInASNParseErrs OBJECT-TYPE
        SYNTAX  Counter
        ACCESS  read-only
        STATUS  mandatory
        DESCRIPTION
        "The total number of ASN.1 or BER errors
        encountered by the SNMP protocol entity when
        decoding received SNMP Messages."
::= { snmp 6 }

snmpInBadCommunityNames OBJECT-TYPE
        SYNTAX  Counter
        ACCESS  read-only
        STATUS  mandatory
        DESCRIPTION
        "The total number of SNMP Messages delivered to
        the SNMP protocol entity which used a SNMP
        community name not known to said entity."
::= { snmp 4 }

snmpInBadCommunityUses OBJECT-TYPE
        SYNTAX  Counter
        ACCESS  read-only
        STATUS  mandatory
        DESCRIPTION
        "The total number of SNMP Messages delivered to
        the SNMP protocol entity which represented an SNMP
        operation which was not allowed by the SNMP
        community named in the Message."
::= { snmp 5 }

snmpInBadValues OBJECT-TYPE
        SYNTAX  Counter
        ACCESS  read-only
        STATUS  mandatory
        DESCRIPTION
        "The total number of SNMP PDUs which were
        delivered to the SNMP protocol entity and for
        which the value of the error-status field is
        `badValue'."
::= { snmp 10 }

snmpInBadVersions OBJECT-TYPE
        SYNTAX  Counter
        ACCESS  read-only
        STATUS  mandatory
        DESCRIPTION
        "The total number of SNMP Messages which were
        delivered to the SNMP protocol entity and were for
        an unsupported SNMP version."
::= { snmp 3 }

snmpInGenErrs OBJECT-TYPE
        SYNTAX  Counter
        ACCESS  read-only
        STATUS  mandatory
        DESCRIPTION
        "The total number of SNMP PDUs which were
        delivered to the SNMP protocol entity and for
        which the value of the error-status field is
        `genErr'."
::= { snmp 12 }

snmpInGetNexts OBJECT-TYPE
        SYNTAX  Counter
        ACCESS  read-only
        STATUS  mandatory
        DESCRIPTION
        "The total number of SNMP Get-Next PDUs which have
        been accepted and processed by the SNMP protocol
        entity."
::= { snmp 16 }

snmpInGetRequests OBJECT-TYPE
        SYNTAX  Counter
        ACCESS  read-only
        STATUS  mandatory
        DESCRIPTION
        "The total number of SNMP Get-Request PDUs which
        have been accepted and processed by the SNMP
        protocol entity."
::= { snmp 15 }

snmpInGetResponses OBJECT-TYPE
        SYNTAX  Counter
        ACCESS  read-only
        STATUS  mandatory
        DESCRIPTION
        "The total number of SNMP Get-Response PDUs which
        have been accepted and processed by the SNMP
        protocol entity."
::= { snmp 18 }

snmpInNoSuchNames OBJECT-TYPE
        SYNTAX  Counter
        ACCESS  read-only
        STATUS  mandatory
        DESCRIPTION
        "The total number of SNMP PDUs which were
        delivered to the SNMP protocol entity and for
        which the value of the error-status field is
        `noSuchName'."
::= { snmp 9 }

snmpInPkts OBJECT-TYPE
        SYNTAX  Counter
        ACCESS  read-only
        STATUS  mandatory
        DESCRIPTION
        "The total number of Messages delivered to the
        SNMP entity from the transport service."
::= { snmp 1 }

snmpInReadOnlys OBJECT-TYPE
        SYNTAX  Counter
        ACCESS  read-only
        STATUS  mandatory
        DESCRIPTION
        "The total number valid SNMP PDUs which were
        delivered to the SNMP protocol entity and for
        which the value of the error-status field is
        `readOnly'.  It should be noted that it is a
        protocol error to generate an SNMP PDU which
        contains the value `readOnly' in the error-status
        field, as such this object is provided as a means
        of detecting incorrect implementations of the
        SNMP."
::= { snmp 11 }

snmpInSetRequests OBJECT-TYPE
        SYNTAX  Counter
        ACCESS  read-only
        STATUS  mandatory
        DESCRIPTION
        "The total number of SNMP Set-Request PDUs which
        have been accepted and processed by the SNMP
        protocol entity."
::= { snmp 17 }

snmpInTooBigs OBJECT-TYPE
        SYNTAX  Counter
        ACCESS  read-only
        STATUS  mandatory
        DESCRIPTION
        "The total number of SNMP PDUs which were
        delivered to the SNMP protocol entity and for
        which the value of the error-status field is
        `tooBig'."
::= { snmp 8 }

snmpInTotalReqVars OBJECT-TYPE
        SYNTAX  Counter
        ACCESS  read-only
        STATUS  mandatory
        DESCRIPTION
        "The total number of MIB objects which have been
        retrieved successfully by the SNMP protocol entity
        as the result of receiving valid SNMP Get-Request
        and Get-Next PDUs."
::= { snmp 13 }

snmpInTotalSetVars OBJECT-TYPE
        SYNTAX  Counter
        ACCESS  read-only
        STATUS  mandatory
        DESCRIPTION
        "The total number of MIB objects which have been
        altered successfully by the SNMP protocol entity
        as the result of receiving valid SNMP Set-Request
        PDUs."
::= { snmp 14 }

snmpInTraps OBJECT-TYPE
        SYNTAX  Counter
        ACCESS  read-only
        STATUS  mandatory
        DESCRIPTION
        "The total number of SNMP Trap PDUs which have
        been accepted and processed by the SNMP protocol
        entity."
::= { snmp 19 }

snmpInvalidMsgs OBJECT-TYPE
        SYNTAX       Counter32
        MAX-ACCESS   read-only
        STATUS       current
        DESCRIPTION "The total number of packets received by the SNMP
        engine which were dropped because there were invalid
        or inconsistent components in the SNMP message.
        "
::= { snmpMPDStats 2 }

snmpOutBadValues OBJECT-TYPE
        SYNTAX  Counter
        ACCESS  read-only
        STATUS  mandatory
        DESCRIPTION
        "The total number of SNMP PDUs which were
        generated by the SNMP protocol entity and for
        which the value of the error-status field is
        `badValue'."
::= { snmp 22 }

snmpOutGenErrs OBJECT-TYPE
        SYNTAX  Counter
        ACCESS  read-only
        STATUS  mandatory
        DESCRIPTION
        "The total number of SNMP PDUs which were
        generated by the SNMP protocol entity and for
        which the value of the error-status field is
        `genErr'."
::= { snmp 24 }

snmpOutGetNexts OBJECT-TYPE
        SYNTAX  Counter
        ACCESS  read-only
        STATUS  mandatory
        DESCRIPTION
        "The total number of SNMP Get-Next PDUs which have
        been generated by the SNMP protocol entity."
::= { snmp 26 }

snmpOutGetRequests OBJECT-TYPE
        SYNTAX  Counter
        ACCESS  read-only
        STATUS  mandatory
        DESCRIPTION
        "The total number of SNMP Get-Request PDUs which
        have been generated by the SNMP protocol entity."
::= { snmp 25 }

snmpOutGetResponses OBJECT-TYPE
        SYNTAX  Counter
        ACCESS  read-only
        STATUS  mandatory
        DESCRIPTION
        "The total number of SNMP Get-Response PDUs which
        have been generated by the SNMP protocol entity."
::= { snmp 28 }

snmpOutNoSuchNames OBJECT-TYPE
        SYNTAX  Counter
        ACCESS  read-only
        STATUS  mandatory
        DESCRIPTION
        "The total number of SNMP PDUs which were
        generated by the SNMP protocol entity and for
        which the value of the error-status is
        `noSuchName'."
::= { snmp 21 }

snmpOutPkts OBJECT-TYPE
        SYNTAX  Counter
        ACCESS  read-only
        STATUS  mandatory
        DESCRIPTION
        "The total number of SNMP Messages which were
        passed from the SNMP protocol entity to the
        transport service."
::= { snmp 2 }

snmpOutSetRequests OBJECT-TYPE
        SYNTAX  Counter
        ACCESS  read-only
        STATUS  mandatory
        DESCRIPTION
        "The total number of SNMP Set-Request PDUs which
        have been generated by the SNMP protocol entity."
::= { snmp 27 }

snmpOutTooBigs OBJECT-TYPE
        SYNTAX  Counter
        ACCESS  read-only
        STATUS  mandatory
        DESCRIPTION
        "The total number of SNMP PDUs which were
        generated by the SNMP protocol entity and for
        which the value of the error-status field is
        `tooBig.'"
::= { snmp 20 }

snmpOutTraps OBJECT-TYPE
        SYNTAX  Counter
        ACCESS  read-only
        STATUS  mandatory
        DESCRIPTION
        "The total number of SNMP Trap PDUs which have
        been generated by the SNMP protocol entity."
::= { snmp 29 }

snmpProxyDrops OBJECT-TYPE
        SYNTAX     Counter32
        MAX-ACCESS read-only
        STATUS     current
        DESCRIPTION
        "The total number of Confirmed Class PDUs
        (such as GetRequest-PDUs, GetNextRequest-PDUs,
        GetBulkRequest-PDUs, SetRequest-PDUs, and
        InformRequest-PDUs) delivered to the SNMP entity which
        were silently dropped because the transmission of
        the (possibly translated) message to a proxy target
        failed in a manner (other than a time-out) such that
        no Response Class PDU (such as a Response-PDU) could
        be returned."
::= { snmp 32 }

snmpSilentDrops OBJECT-TYPE
        SYNTAX     Counter32
        MAX-ACCESS read-only
        STATUS     current
        DESCRIPTION
        "The total number of Confirmed Class PDUs (such as
        GetRequest-PDUs, GetNextRequest-PDUs,
        GetBulkRequest-PDUs, SetRequest-PDUs, and
        InformRequest-PDUs) delivered to the SNMP entity which
        were silently dropped because the size of a reply
        containing an alternate Response Class PDU (such as a
        Response-PDU) with an empty variable-bindings field
        was greater than either a local constraint or the
        maximum message size associated with the originator of
        the request."
::= { snmp 31 }

snmpTargetAddrName OBJECT-TYPE
        SYNTAX      SnmpAdminString (SIZE(1..32))
        MAX-ACCESS  not-accessible
        STATUS      current
        DESCRIPTION
        "The locally arbitrary, but unique identifier associated
        with this snmpTargetAddrEntry."
::= { snmpTargetAddrEntry 1 }

snmpTargetAddrParams OBJECT-TYPE
        SYNTAX      SnmpAdminString (SIZE(1..32))
        MAX-ACCESS  read-create
        STATUS      current
        DESCRIPTION
        "The value of this object identifies an entry in the
        snmpTargetParamsTable.  The identified entry
        contains SNMP parameters to be used when generating
        messages to be sent to this transport address."
::= { snmpTargetAddrEntry 7 }

snmpTargetAddrRetryCount OBJECT-TYPE
        SYNTAX      Integer32 (0..255)
        MAX-ACCESS  read-create
        STATUS      current
        DESCRIPTION
        "This object specifies a default number of retries to be
        attempted when a response is not received for a generated
        message.  An application may provide its own retry count,
        in which case the value of this object is ignored."
        DEFVAL { 3 }
::= { snmpTargetAddrEntry 5 }

snmpTargetAddrRowStatus OBJECT-TYPE
        SYNTAX      RowStatus
        MAX-ACCESS  read-create
        STATUS      current
        DESCRIPTION
        "The status of this conceptual row.
        To create a row in this table, a manager must
        set this object to either createAndGo(4) or
        createAndWait(5).
        Until instances of all corresponding columns are
        appropriately configured, the value of the
        corresponding instance of the snmpTargetAddrRowStatus
        column is 'notReady'.
        In particular, a newly created row cannot be made
        active until the corresponding instances of
        snmpTargetAddrTDomain, snmpTargetAddrTAddress, and
        snmpTargetAddrParams have all been set.
        The following objects may not be modified while the
        value of this object is active(1):
        - snmpTargetAddrTDomain
        - snmpTargetAddrTAddress
        An attempt to set these objects while the value of
        snmpTargetAddrRowStatus is active(1) will result in
        an inconsistentValue error."
::= { snmpTargetAddrEntry 9 }

snmpTargetAddrStorageType OBJECT-TYPE
        SYNTAX      StorageType
        MAX-ACCESS  read-create
        STATUS      current
        DESCRIPTION
        "The storage type for this conceptual row.
        Conceptual rows having the value 'permanent' need not
        allow write-access to any columnar objects in the row."
        DEFVAL { nonVolatile }
::= { snmpTargetAddrEntry 8 }

snmpTargetAddrTAddress OBJECT-TYPE
        SYNTAX      TAddress
        MAX-ACCESS  read-create
        STATUS      current
        DESCRIPTION
        "This object contains a transport address.  The format of
        this address depends on the value of the
        snmpTargetAddrTDomain object."
::= { snmpTargetAddrEntry 3 }

snmpTargetAddrTDomain OBJECT-TYPE
        SYNTAX      TDomain
        MAX-ACCESS  read-create
        STATUS      current
        DESCRIPTION
        "This object indicates the transport type of the address
        contained in the snmpTargetAddrTAddress object."
::= { snmpTargetAddrEntry 2 }

snmpTargetAddrTagList OBJECT-TYPE
        SYNTAX      SnmpTagList
        MAX-ACCESS  read-create
        STATUS      current
        DESCRIPTION
        "This object contains a list of tag values which are
        used to select target addresses for a particular
        operation."
        DEFVAL { "" }
::= { snmpTargetAddrEntry 6 }

snmpTargetAddrTimeout OBJECT-TYPE
        SYNTAX      TimeInterval
        MAX-ACCESS  read-create
        STATUS      current
        DESCRIPTION
        "This object should reflect the expected maximum round
        trip time for communicating with the transport address
        defined by this row.  When a message is sent to this
        address, and a response (if one is expected) is not
        received within this time period, an implementation
        may assume that the response will not be delivered.
        Note that the time interval that an application waits
        for a response may actually be derived from the value
        of this object.  The method for deriving the actual time
        interval is implementation dependent.  One such method
        is to derive the expected round trip time based on a
        particular retransmission algorithm and on the number
        of timeouts which have occurred.  The type of message may
        also be considered when deriving expected round trip
        times for retransmissions.  For example, if a message is
        being sent with a securityLevel that indicates both
        authentication and privacy, the derived value may be
        increased to compensate for extra processing time spent
        during authentication and encryption processing."
        DEFVAL { 1500 }
::= { snmpTargetAddrEntry 4 }

snmpUnknownPDUHandlers OBJECT-TYPE
        SYNTAX       Counter32
        MAX-ACCESS   read-only
        STATUS       current
        DESCRIPTION "The total number of packets received by the SNMP
        engine which were dropped because the PDU contained
        in the packet could not be passed to an application
        responsible for handling the pduType, e.g. no SNMP
        application had registered for the proper
        combination of the contextEngineID and the pduType.
        "
::= { snmpMPDStats 3 }

snmpUnknownSecurityModels OBJECT-TYPE
        SYNTAX       Counter32
        MAX-ACCESS   read-only
        STATUS       current
        DESCRIPTION "The total number of packets received by the SNMP
        engine which were dropped because they referenced a
        securityModel that was not known to or supported by
        the SNMP engine.
        "
::= { snmpMPDStats 1 }

speed-energy-usage OBJECT-TYPE
        SYNTAX     INTEGER {
        eFasterFirstPage(1),
        eSaveEnergy(2),
        eSaveMostEnergy(3),
        eSaveMoreEnergy(4)
        }
        ACCESS     read-write
        STATUS      optional
        DESCRIPTION "Option to keep the engine in a pre-warmed state to speed up
        first page out."
::={ settings-system 50 }

start-engine-early-warmup OBJECT-TYPE
        SYNTAX  INTEGER {
        eValue1(1)
        }
        ACCESS  write-only
        STATUS  mandatory
        DESCRIPTION
        "This PML object is used by HP SW drivers to signal the printer
        that a job is coming, and to start the warm-up process
        early.The effect of warming up early will reduce the First Page
        Out time."
::= { settings-system 99 }

sysContact OBJECT-TYPE
        SYNTAX  DisplayString (SIZE (0..255))
        ACCESS  read-write
        STATUS  mandatory
        DESCRIPTION
        "The textual identification of the contact person
        for this managed node, together with information
        on how to contact this person."
::= { system 4 }

sysDescr OBJECT-TYPE
        SYNTAX  DisplayString (SIZE (0..255))
        ACCESS  read-only
        STATUS  mandatory
        DESCRIPTION
        "A textual description of the entity.  This value
        should include the full name and version
        identification of the system's hardware type,
        software operating-system, and networking
        software.  It is mandatory that this only contain
        printable ASCII characters."
::= { system 1 }

sysLocation OBJECT-TYPE
        SYNTAX  DisplayString (SIZE (0..255))
        ACCESS  read-write
        STATUS  mandatory
        DESCRIPTION
        "The physical location of this node (e.g.,
        `telephone closet, 3rd floor')."
::= { system 6 }

sysName OBJECT-TYPE
        SYNTAX  DisplayString (SIZE (0..255))
        ACCESS  read-write
        STATUS  mandatory
        DESCRIPTION
        "An administratively-assigned name for this
        managed node.  By convention, this is the node's
        fully-qualified domain name."
::= { system 5 }

sysORLastChange OBJECT-TYPE
        SYNTAX     TimeStamp
        MAX-ACCESS read-only
        STATUS     current
        DESCRIPTION
        "The value of sysUpTime at the time of the most recent
        change in state or value of any instance of sysORID."
::= { system 8 }

sysObjectID OBJECT-TYPE
        SYNTAX  OBJECT IDENTIFIER
        ACCESS  read-only
        STATUS  mandatory
        DESCRIPTION
        "The vendor's authoritative identification of the
        network management subsystem contained in the
        entity.  This value is allocated within the SMI
        enterprises subtree (1.3.6.1.4.1) and provides an
        easy and unambiguous means for determining `what
        kind of box' is being managed.  For example, if
        vendor `Flintstones, Inc.' was assigned the
        subtree 1.3.6.1.4.1.4242, it could assign the
        identifier 1.3.6.1.4.1.4242.1.1 to its `Fred
        Router'."
::= { system 2 }

sysServices OBJECT-TYPE
        SYNTAX  INTEGER (0..127)
        ACCESS  read-only
        STATUS  mandatory
        DESCRIPTION
        "A value which indicates the set of services that
        this entity primarily offers.
        The value is a sum.  This sum initially takes the
        value zero, Then, for each layer, L, in the range
        1 through 7, that this node performs transactions
        for, 2 raised to (L - 1) is added to the sum.  For
        example, a node which performs primarily routing
        functions would have a value of 4 (2^(3-1)).  In
        contrast, a node which is a host offering
        application services would have a value of 72
        (2^(4-1) + 2^(7-1)).  Note that in the context of
        the Internet suite of protocols, values should be
        calculated accordingly:
        layer  functionality
        1  physical (e.g., repeaters)
        2  datalink/subnetwork (e.g., bridges)
        3  internet (e.g., IP gateways)
        4  end-to-end  (e.g., IP hosts)
        7  applications (e.g., mail relays)
        For systems including OSI protocols, layers 5 and
        6 may also be counted."
::= { system 7 }

sysUpTime OBJECT-TYPE
        SYNTAX  TimeTicks
        ACCESS  read-only
        STATUS  mandatory
        DESCRIPTION
        "The time (in hundredths of a second) since the
        network management portion of the system was last
        re-initialized."
::= { system 3 }

total-color-page-count OBJECT-TYPE
        SYNTAX  INTEGER
        ACCESS  read-only
        STATUS  optional
        DESCRIPTION
        "Total number of color pages printed by the device.
        Additional information:
        Any page with one or more color pixels is counted as a color page. Pages that only
        contain black marks are not counted by this object.
        A duplexed sheet of media will cause the counter to be incremented by two."
::= { status-prt-eng 7 }

total-engine-page-count OBJECT-TYPE
        SYNTAX     INTEGER
        ACCESS     read-write
        STATUS      optional
        DESCRIPTION "Total number of pages printed by the device. POS indicates if
        the total engine page count is kept in NVRAM, and the maximum
        supported value before the page count rolls over to zero."
::= { status-prt-eng 5 }

total-mono-page-count OBJECT-TYPE
        SYNTAX     INTEGER
        ACCESS     read-only
        STATUS      optional
        DESCRIPTION "Total number of black pages printed by the device."
::= { status-prt-eng 6 }

trapAddrFamily			OBJECT-TYPE
        SYNTAX		Integer32
        MAX-ACCESS	read-write
        STATUS		current
        DESCRIPTION
        "Protocol family for trap.  Possible values:
        0  not_SET
        1  af_UDP
        2  af_IPX
        3  af_LLC
        4  af_DDP"
::=  {  trapDestinationEntry  1  }

trapAddrIp			OBJECT-TYPE
        SYNTAX		IpAddress
        MAX-ACCESS	read-write
        STATUS		current
        DESCRIPTION
        "Ip address of trap destination."
::=  {  trapDestinationEntry  2  }

trapBaseTimeout			OBJECT-TYPE
        SYNTAX		Integer32
        MAX-ACCESS	read-write
        STATUS		current
        DESCRIPTION
        "Applicable only if trapVersion is set to Inform.
        Units are 1/10 second intervals.  Default is 2
        corresponding to 200 milliseconds.  This value corresponds
        to the time of the first retry following the initial inform
        request. Additional retries are sent at times corresponding to
        the retry number multiplied by the trapBaseTimeout.
        This value remains persistent through a powercycle."
::=  {  trapDestinationEntry  6  }

trapCommunityName		OBJECT-TYPE
        SYNTAX		OCTET STRING
        MAX-ACCESS	read-write
        STATUS		current
        DESCRIPTION
        "Trap community name specified in the trap packet."
::=  {  trapDestinationEntry  4  }

trapDestOwner			OBJECT-TYPE
        SYNTAX		INTEGER  { oldStylePML ( 1 ) , brady ( 2 ) , oldStyleAndBRADY ( 3 ) }
        MAX-ACCESS	read-only
        STATUS		current
        DESCRIPTION
        "This OID is read only. It is used to monitor the insertion and removal
        of a trap destination entry. It is controlled by the corresponding BRADY
        and old style PML registrations."
::=  {  trapDestinationEntry  8  }

trapDestinationNum	OBJECT-TYPE
        SYNTAX			Integer32
        MAX-ACCESS		read-only
        STATUS			current
        DESCRIPTION
        "The number of trap destinations."
::=  {  trapDest  1  }

trapFQDN			OBJECT-TYPE
        SYNTAX		OCTET STRING  ( SIZE ( 0 .. 255  ) )
        MAX-ACCESS	read-write
        STATUS		current
        DESCRIPTION
        "The trap destination's FQDN. This will be resolved to IP address(es) at trap destination time."
::=  {  trapFQDNEntry  2  }

trapFQDNNum	OBJECT-TYPE
        SYNTAX			Integer32
        MAX-ACCESS		read-only
        STATUS			current
        DESCRIPTION
        "Number of trapFQDNTable rows."
::=  {  trapDest  6  }

trapFilterDelay	OBJECT-TYPE
        SYNTAX			Integer32
        MAX-ACCESS		read-write
        STATUS			current
        DESCRIPTION
        "The purpose of the trap filter feature is to prevent multiple traps
        of the same specificTrapId to be sent within a short period of time.
        This object assigns the period of time within which a duplicate trap
        will be blocked.  This value is in 1/10 second intervals and the default
        value is set to 50 corresponding to 5 seconds. This value remains
        persistent
        through a powercycle."
::=  {  trapDest  5  }

trapIPAddress			OBJECT-TYPE
        SYNTAX		IpAddress
        MAX-ACCESS	read-only
        STATUS		current
        DESCRIPTION
        "The trap destination IP address."
::=  {  trapFQDNEntry  1  }

trapPort			OBJECT-TYPE
        SYNTAX		Integer32
        MAX-ACCESS	read-write
        STATUS		current
        DESCRIPTION
        "Host port to which traps are sent."
::=  {  trapDestinationEntry  3  }

trapRetryNum			OBJECT-TYPE
        SYNTAX		Integer32
        MAX-ACCESS	read-write
        STATUS		current
        DESCRIPTION
        "This is the maximum number of inform retries that will be sent to
        this destination.  Retries are sent if no inform reply is received
        within the timeout value.  The timeout value is calculated as
        described under trapBaseTimeout.
        This value remains persistent through a powercycle."
::=  {  trapDestinationEntry  7  }

trapSource	OBJECT-TYPE
        SYNTAX			Integer32
        MAX-ACCESS		read-only
        STATUS			current
        DESCRIPTION
        "Sets the agent internal source for traps.  Possibilities are as follows:
        0 = ALL_TRAPS_ON
        1 = ASYNC_PERIPHERAL_STATUS traps only
        2 = proprietary PML traps only
        3 = alert table traps only
        This object was changed to read-only to accommodate the SNMPv3
        Notifiaction tables requirement to recieve all traps.  SNMPv3 tags
        are used to filter SNMP Trap sources."
::=  {  trapDest  4  }

trapTest	OBJECT-TYPE
        SYNTAX			Integer32
        MAX-ACCESS		read-write
        STATUS			current
        DESCRIPTION
        "Causes agent to send an snmp trap to hosts registered in the trap
        destination table.  Value specified will be used as the specific
        trap id."
::=  {  trapDest  3  }

trapVersion			OBJECT-TYPE
        SYNTAX		Integer32
        MAX-ACCESS	read-write
        STATUS		current
        DESCRIPTION
        "Trap version, one of the following
        0 = snmpV1
        1 = snmpV2
        3 = Inform
        Default is  0 = snmpV1.
        This value remains persistent through a powercycle."
::=  {  trapDestinationEntry  5  }

tray1-custom-media-length OBJECT-TYPE
        SYNTAX  INTEGER
        ACCESS  read-only
        STATUS  optional
        DESCRIPTION
        "Length of media (in decipoints) loaded in tray 1."
::= { intray1 11 }

tray1-custom-media-width		OBJECT-TYPE
        SYNTAX		INTEGER
        ACCESS		read-only
        STATUS		optional
        DESCRIPTION "Width of media (in decipoints) loaded in tray 1."
::= { intray1 10 }

tray1-media-key OBJECT-TYPE
        SYNTAX  OCTET STRING
        ACCESS  read-only
        STATUS  optional
        DESCRIPTION
        "Contains the media key (index) in the database."
::= { intray1 20 }

tray1-media-name OBJECT-TYPE
        SYNTAX  OCTET STRING
        ACCESS  read-write
        STATUS  optional
        DESCRIPTION
        "Contains a string identifying the media that is currently
        loaded in tray #1. The media name string is the name associated
        with the loaded media. The strings identifying different media
        are user defined. Examples media name strings include 'HR
        Company LetterHead', '1091 Invoice Form', 'White Bond',
        'Canary', and 'White Recycled'."
::= { intray1 4 }

tray1-media-size-loaded OBJECT-TYPE
        SYNTAX  INTEGER {
        eAnySize(32765),
		eUSLetter(2),
		eUSLegal(3),
		eUSExecutive(1),
		eFoolscap(10),
		eIndexCard4x6(74),
		eIndexCard5x8(75),
		eISOandJISA4(26),
		eISOandJISA5(25),
		eISOandJISA6(24),
		eJISB6(44),
		eJISB5(45),
		ePhoto10x15(118),
		eLegal216x340(127),
		eROC16K(17),
		ePRC16K195X270(34),
		ePRC16K184X260(89),
		eJapansePostcardSingle(71),
		eJapansePostcardDouble(72),
		eMonarch(80),
		eCommercial10(81),
		eInternationalB5(100),
		eInternationalDL(90),
		eInternationalC5(91),
		eCustom(101)
        }
        ACCESS  read-write
        STATUS  optional
        DESCRIPTION
        "Returns the media size that is currently configuredconfigured
        in tray #1. This object can be set to indicate the media size
        currently loaded, if the printer supports input trays that can
        not sense the media size."
::= { intray1 1 }

tray1-type OBJECT-TYPE
        SYNTAX  INTEGER {
        eTray(1),
        eManualRoll(2),
        eArss(3),
        eManualSheet(4)
        }
        ACCESS  read-write
        STATUS  optional
        DESCRIPTION
        "Indicates the type of input media support installed. eTray (1)
        if the paper source is a tray eManualRoll (2) if the paper
        source is a manually loaded roll eArss (3) if the paper source
        is an anutomatically loaded roll (ARSS) eManualSheet (4) if the
        paper source is only for a manually loaded single sheet"
::= { intray1 17 }

tray2-custom-media-length OBJECT-TYPE
        SYNTAX  INTEGER
        ACCESS  read-only
        STATUS  optional
        DESCRIPTION
        "Length of media (in decipoints) loaded in tray 2."
::= { intray2 11 }

tray2-custom-media-width		OBJECT-TYPE
        SYNTAX	   INTEGER
        ACCESS     read-only
        STATUS     optional
        DESCRIPTION "Width of media (in decipoints) loaded in tray 2."
::= { intray2 10 }

tray2-media-key OBJECT-TYPE
        SYNTAX  OCTET STRING
        ACCESS  read-only
        STATUS  optional
        DESCRIPTION
        "Contains the media key (index) in the database."
::= { intray2 20 }

tray2-media-name OBJECT-TYPE
        SYNTAX  OCTET STRING
        ACCESS  read-write
        STATUS  optional
        DESCRIPTION
        "Contains a string identifying the media that is currently
        loaded in tray 2. See TRAY1-MEDIA-NAME for a complete
        description."
::= { intray2 4 }

tray2-media-size-loaded OBJECT-TYPE
        SYNTAX  INTEGER {
        eAnySize(32765),
		eUSLetter(2),
		eUSLegal(3),
		eUSExecutive(1),
		eFoolscap(10),
		eIndexCard4x6(74),
		eIndexCard5x8(75),
		eISOandJISA4(26),
		eISOandJISA5(25),
		eISOandJISA6(24),
		eJISB6(44),
		eJISB5(45),
		ePhoto10x15(118),
		eLegal216x340(127),
		eROC16K(17),
		ePRC16K195X270(34),
		ePRC16K184X260(89),
		eJapansePostcardSingle(71),
		eJapansePostcardDouble(72),
		eMonarch(80),
		eCommercial10(81),
		eInternationalB5(100),
		eInternationalDL(90),
		eInternationalC5(91),
		eCustom(101)
        }
        ACCESS  read-write
        STATUS  optional
        DESCRIPTION
        "Returns the media size that is currently configured in tray #2."
::= { intray2 1 }

tray2-type OBJECT-TYPE
        SYNTAX  INTEGER {
        eTray(1),
        eManualRoll(2),
        eArss(3),
        eManualSheet(4)
        }
        ACCESS  read-write
        STATUS  optional
        DESCRIPTION
        "Indicates the type of input media support installed. eTray (1)
        if the paper source is a tray eManualRoll (2) if the paper
        source is a manually loaded roll eArss (3) if the paper source
        is an anutomatically loaded roll (ARSS) eManualSheet (4) if the
        paper source is only for a manually loaded single sheet"
::= { intray2 17 }

usage-average-toner-coverage OBJECT-TYPE
        SYNTAX  OCTET STRING
        ACCESS  read-only
        STATUS  optional
        DESCRIPTION
        "Reports the average toner area coverage of all pages printed
        over the life of the device. Counts pixels on each page,
        divides pixel count by pixels possible on a page to give the
        percentage of coverage, and keeps a rolling average percent
        weighted by area printed."
::= { printer-accounting 3 }

usage-printer-color-total-charge OBJECT-TYPE
        SYNTAX  OCTET STRING
        ACCESS  read-only
        STATUS  optional
        DESCRIPTION
        "Total printer charge for all paper sizes printed in color
        only.
        Additional information:
        This is the total charge over the range of all
        supported media sizes for duplex and simplex color
        pages."
::= { printer-accounting 13 }

usage-printer-mono-total-charge OBJECT-TYPE
        SYNTAX  OCTET STRING
        ACCESS  read-only
        STATUS  optional
        DESCRIPTION
        "Total printer charge for all paper sizes printed in monochrome
        only.
        Additional information:
        This is the total charge over the range of all
        supported media sizes for duplex and simplex mono
        pages."
::= { printer-accounting 12 }

usage-printer-total-charge OBJECT-TYPE
        SYNTAX  OCTET STRING
        ACCESS  read-only
        STATUS  optional
        DESCRIPTION
        "Total printer charge for all paper sizes printed."
::= { printer-accounting 2 }

usage-scanner-total-charge OBJECT-TYPE
        SYNTAX  OCTET STRING
        ACCESS  read-only
        STATUS  optional
        DESCRIPTION
        "Total scanner charge or cost for all paper sizes scanned."
::= { scanner-accounting 2 }

usage-staple-count OBJECT-TYPE
        SYNTAX  INTEGER(0..930576247)
        ACCESS  read-only
        STATUS  optional
        DESCRIPTION
        "Total number of staples used."
::= { printer-accounting 4 }

usmStatsDecryptionErrors OBJECT-TYPE
        SYNTAX       Counter32
        MAX-ACCESS   read-only
        STATUS       current
        DESCRIPTION "The total number of packets received by the SNMP
        engine which were dropped because they could not be
        decrypted.
        "
::= { usmStats 6 }

usmStatsNotInTimeWindows OBJECT-TYPE
        SYNTAX       Counter32
        MAX-ACCESS   read-only
        STATUS       current
        DESCRIPTION "The total number of packets received by the SNMP
        engine which were dropped because they appeared
        outside of the authoritative SNMP engine's window.
        "
::= { usmStats 2 }

usmStatsUnknownEngineIDs OBJECT-TYPE
        SYNTAX       Counter32
        MAX-ACCESS   read-only
        STATUS       current
        DESCRIPTION "The total number of packets received by the SNMP
        engine which were dropped because they referenced an
        snmpEngineID that was not known to the SNMP engine.
        "
::= { usmStats 4 }

usmStatsUnknownUserNames OBJECT-TYPE
        SYNTAX       Counter32
        MAX-ACCESS   read-only
        STATUS       current
        DESCRIPTION "The total number of packets received by the SNMP
        engine which were dropped because they referenced a
        user that was not known to the SNMP engine.
        "
::= { usmStats 3 }

usmStatsUnsupportedSecLevels OBJECT-TYPE
        SYNTAX       Counter32
        MAX-ACCESS   read-only
        STATUS       current
        DESCRIPTION "The total number of packets received by the SNMP
        engine which were dropped because they requested a
        securityLevel that was unknown to the SNMP engine
        or otherwise unavailable.
        "
::= { usmStats 1 }

usmStatsWrongDigests OBJECT-TYPE
        SYNTAX       Counter32
        MAX-ACCESS   read-only
        STATUS       current
        DESCRIPTION "The total number of packets received by the SNMP
        engine which were dropped because they didn't
        contain the expected digest value.
        "
::= { usmStats 5 }

usmUserOwnAuthKeyChange OBJECT-TYPE
        SYNTAX       KeyChange   -- typically (SIZE (0 | 32)) for HMACMD5
                                 -- typically (SIZE (0 | 40)) for HMACSHA
        MAX-ACCESS   read-create
        STATUS       current
        DESCRIPTION "Behaves exactly as usmUserAuthKeyChange, with one
        notable difference: in order for the set operation
        to succeed, the usmUserName of the operation
        requester must match the usmUserName that
        indexes the row which is targeted by this
        operation.
        In addition, the USM security model must be
        used for this operation.
        The idea here is that access to this column can be
        public, since it will only allow a user to change
        his own secret authentication key (authKey).
        Note that this can only be done once the row is active.
        When a set is received and the usmUserName of the
        requester is not the same as the umsUserName that
        indexes the row which is targeted by this operation,
        then a 'noAccess' error must be returned.
        When a set is received and the security model in use
        is not USM, then a 'noAccess' error must be returned.
        "
        DEFVAL      { ''H }    -- the empty string
::= { usmUserEntry 7 }

usmUserAuthKeyChange OBJECT-TYPE
        SYNTAX       KeyChange   -- typically (SIZE (0 | 32)) for HMACMD5
        -- typically (SIZE (0 | 40)) for HMACSHA
        MAX-ACCESS   read-create
        STATUS       current
        DESCRIPTION "An object, which when modified, causes the secret
        authentication key used for messages sent on behalf
        of this user to/from the SNMP engine identified by
        usmUserEngineID, to be modified via a one-way
        function.
        The associated protocol is the usmUserAuthProtocol.
        The associated secret key is the user's secret
        authentication key (authKey). The associated hash
        algorithm is the algorithm used by the user's
        usmUserAuthProtocol.
        When creating a new user, it is an 'inconsistentName'
        error for a set operation to refer to this object
        unless it is previously or concurrently initialized
        through a set operation on the corresponding instance
        of usmUserCloneFrom.
        When the value of the corresponding usmUserAuthProtocol
        is usmNoAuthProtocol, then a set is successful, but
        effectively is a no-op.
        When this object is read, the zero-length (empty)
        string is returned.
        The recommended way to do a key change is as follows:
        1) GET(usmUserSpinLock.0) and save in sValue.
        2) generate the keyChange value based on the old
        (existing) secret key and the new secret key,
        let us call this kcValue.
        If you do the key change on behalf of another user:
        3) SET(usmUserSpinLock.0=sValue,
        usmUserAuthKeyChange=kcValue
        usmUserPublic=randomValue)
        If you do the key change for yourself:
        4) SET(usmUserSpinLock.0=sValue,
        usmUserOwnAuthKeyChange=kcValue
        usmUserPublic=randomValue)
        If you get a response with error-status of noError,
        then the SET succeeded and the new key is active.
        If you do not get a response, then you can issue a
        GET(usmUserPublic) and check if the value is equal
        to the randomValue you did send in the SET. If so, then
        the key change succeeded and the new key is active
        (probably the response got lost). If not, then the SET
        request probably never reached the target and so you
        can start over with the procedure above.
        "
        DEFVAL      { ''H }    -- the empty string
::= { usmUserEntry 6 }

usmUserAuthProtocol OBJECT-TYPE
        SYNTAX       AutonomousType
        MAX-ACCESS   read-create
        STATUS       current
        DESCRIPTION "An indication of whether messages sent on behalf of
        this user to/from the SNMP engine identified by
        usmUserEngineID, can be authenticated, and if so,
        the type of authentication protocol which is used.
        An instance of this object is created concurrently
        with the creation of any other object instance for
        the same user (i.e., as part of the processing of
        the set operation which creates the first object
        instance in the same conceptual row).
        If an initial set operation (i.e. at row creation time)
        tries to set a value for an unknown or unsupported
        protocol, then a 'wrongValue' error must be returned.
        The value will be overwritten/set when a set operation
        is performed on the corresponding instance of
        usmUserCloneFrom.
        Once instantiated, the value of such an instance of
        this object can only be changed via a set operation to
        the value of the usmNoAuthProtocol.
        If a set operation tries to change the value of an
        existing instance of this object to any value other
        than usmNoAuthProtocol, then an 'inconsistentValue'
        error must be returned.
        If a set operation tries to set the value to the
        usmNoAuthProtocol while the usmUserPrivProtocol value
        in the same row is not equal to usmNoPrivProtocol,
        then an 'inconsistentValue' error must be returned.
        That means that an SNMP command generator application
        must first ensure that the usmUserPrivProtocol is set
        to the usmNoPrivProtocol value before it can set
        the usmUserAuthProtocol value to usmNoAuthProtocol.
        "
        DEFVAL      { usmNoAuthProtocol }
::= { usmUserEntry 5 }

usmUserCloneFrom OBJECT-TYPE
        SYNTAX       RowPointer
        MAX-ACCESS   read-create
        STATUS       current
        DESCRIPTION "A pointer to another conceptual row in this
        usmUserTable.  The user in this other conceptual
        row is called the clone-from user.
        When a new user is created (i.e., a new conceptual
        row is instantiated in this table), the privacy and
        authentication parameters of the new user must be
        cloned from its clone-from user. These parameters are:
        - authentication protocol (usmUserAuthProtocol)
        - privacy protocol (usmUserPrivProtocol)
        They will be copied regardless of what the current
        value is.
        Cloning also causes the initial values of the secret
        authentication key (authKey) and the secret encryption
        key (privKey) of the new user to be set to the same
        values as the corresponding secrets of the clone-from
        user to allow the KeyChange process to occur as
        required during user creation.
        The first time an instance of this object is set by
        a management operation (either at or after its
        instantiation), the cloning process is invoked.
        Subsequent writes are successful but invoke no
        action to be taken by the receiver.
        The cloning process fails with an 'inconsistentName'
        error if the conceptual row representing the
        clone-from user does not exist or is not in an active
        state when the cloning process is invoked.
        When this object is read, the ZeroDotZero OID
        is returned.
        "
::= { usmUserEntry 4 }

usmUserOwnPrivKeyChange OBJECT-TYPE
        SYNTAX       KeyChange  -- typically (SIZE (0 | 32)) for DES
        MAX-ACCESS   read-create
        STATUS       current
        DESCRIPTION "Behaves exactly as usmUserPrivKeyChange, with one
        notable difference: in order for the Set operation
        to succeed, the usmUserName of the operation
        requester must match the usmUserName that indexes
        the row which is targeted by this operation.
        In addition, the USM security model must be
        used for this operation.
        The idea here is that access to this column can be
        public, since it will only allow a user to change
        his own secret privacy key (privKey).
        Note that this can only be done once the row is active.
        When a set is received and the usmUserName of the
        requester is not the same as the umsUserName that
        indexes the row which is targeted by this operation,
        then a 'noAccess' error must be returned.
        When a set is received and the security model in use
        is not USM, then a 'noAccess' error must be returned.
        "
        DEFVAL      { ''H }    -- the empty string
::= { usmUserEntry 10 }

usmUserPrivKeyChange OBJECT-TYPE
        SYNTAX       KeyChange  -- typically (SIZE (0 | 32)) for DES
        MAX-ACCESS   read-create
        STATUS       current
        DESCRIPTION "An object, which when modified, causes the secret
        encryption key used for messages sent on behalf
        of this user to/from the SNMP engine identified by
        usmUserEngineID, to be modified via a one-way
        function.
        The associated protocol is the usmUserPrivProtocol.
        The associated secret key is the user's secret
        privacy key (privKey). The associated hash
        algorithm is the algorithm used by the user's
        usmUserAuthProtocol.
        When creating a new user, it is an 'inconsistentName'
        error for a set operation to refer to this object
        unless it is previously or concurrently initialized
        through a set operation on the corresponding instance
        of usmUserCloneFrom.
        When the value of the corresponding usmUserPrivProtocol
        is usmNoPrivProtocol, then a set is successful, but
        effectively is a no-op.
        When this object is read, the zero-length (empty)
        string is returned.
        See the description clause of usmUserAuthKeyChange for
        a recommended procedure to do a key change.
        "
        DEFVAL      { ''H }    -- the empty string
::= { usmUserEntry 9 }

usmUserPrivProtocol OBJECT-TYPE
        SYNTAX       AutonomousType
        MAX-ACCESS   read-create
        STATUS       current
        DESCRIPTION "An indication of whether messages sent on behalf of
        this user to/from the SNMP engine identified by
        usmUserEngineID, can be protected from disclosure,
        and if so, the type of privacy protocol which is used.
        An instance of this object is created concurrently
        with the creation of any other object instance for
        the same user (i.e., as part of the processing of
        the set operation which creates the first object
        instance in the same conceptual row).
        If an initial set operation (i.e. at row creation time)
        tries to set a value for an unknown or unsupported
        protocol, then a 'wrongValue' error must be returned.
        The value will be overwritten/set when a set operation
        is performed on the corresponding instance of
        usmUserCloneFrom.
        Once instantiated, the value of such an instance of
        this object can only be changed via a set operation to
        the value of the usmNoPrivProtocol.
        If a set operation tries to change the value of an
        existing instance of this object to any value other
        than usmNoPrivProtocol, then an 'inconsistentValue'
        error must be returned.
        Note that if any privacy protocol is used, then you
        must also use an authentication protocol. In other
        words, if usmUserPrivProtocol is set to anything else
        than usmNoPrivProtocol, then the corresponding instance
        of usmUserAuthProtocol cannot have a value of
        usmNoAuthProtocol. If it does, then an
        'inconsistentValue' error must be returned.
        "
        DEFVAL      { usmNoPrivProtocol }
::= { usmUserEntry 8 }

usmUserPublic    OBJECT-TYPE
        SYNTAX       OCTET STRING (SIZE(0..32))
        MAX-ACCESS   read-create
        STATUS       current
        DESCRIPTION "A publicly-readable value which can be written as part
        of the procedure for changing a user's secret
        authentication and/or privacy key, and later read to
        determine whether the change of the secret was
        effected.
        "
        DEFVAL      { ''H }  -- the empty string
::= { usmUserEntry 11 }

usmUserSecurityName OBJECT-TYPE
        SYNTAX       SnmpAdminString
        MAX-ACCESS   read-only
        STATUS       current
        DESCRIPTION "A human readable string representing the user in
        Security Model independent format.
        The default transformation of the User-based Security
        Model dependent security ID to the securityName and
        vice versa is the identity function so that the
        securityName is the same as the userName.
        "
::= { usmUserEntry 3 }

usmUserSpinLock  OBJECT-TYPE
        SYNTAX       TestAndIncr
        MAX-ACCESS   read-write
        STATUS       current
        DESCRIPTION "An advisory lock used to allow several cooperating
        Command Generator Applications to coordinate their
        use of facilities to alter secrets in the
        usmUserTable.
        "
::= { usmUser 1 }

usmUserStatus    OBJECT-TYPE
        SYNTAX       RowStatus
        MAX-ACCESS   read-create
        STATUS       current
        DESCRIPTION "The status of this conceptual row.
        Until instances of all corresponding columns are
        appropriately configured, the value of the
        corresponding instance of the usmUserStatus column
        is 'notReady'.
        In particular, a newly created row for a user who
        employs authentication, cannot be made active until the
        corresponding usmUserCloneFrom and usmUserAuthKeyChange
        have been set.
        Further, a newly created row for a user who also
        employs privacy, cannot be made active until the
        usmUserPrivKeyChange has been set.
        The RowStatus TC [RFC2579] requires that this
        DESCRIPTION clause states under which circumstances
        other objects in this row can be modified:
        The value of this object has no effect on whether
        other objects in this conceptual row can be modified,
        except for usmUserOwnAuthKeyChange and
        usmUserOwnPrivKeyChange. For these 2 objects, the
        value of usmUserStatus MUST be active.
        "
::= { usmUserEntry 13 }

usmUserStorageType OBJECT-TYPE
        SYNTAX       StorageType
        MAX-ACCESS   read-create
        STATUS       current
        DESCRIPTION "The storage type for this conceptual row.
        Conceptual rows having the value 'permanent' must
        allow write-access at a minimum to:
        - usmUserAuthKeyChange, usmUserOwnAuthKeyChange
        and usmUserPublic for a user who employs
        authentication, and
        - usmUserPrivKeyChange, usmUserOwnPrivKeyChange
        and usmUserPublic for a user who employs
        privacy.
        Note that any user who employs authentication or
        privacy must allow its secret(s) to be updated and
        thus cannot be 'readOnly'.
        If an initial set operation tries to set the value to
        'readOnly' for a user who employs authentication or
        privacy, then an 'inconsistentValue' error must be
        returned.  Note that if the value has been previously
        set (implicit or explicit) to any value, then the rules
        as defined in the StorageType Textual Convention apply.
        It is an implementation issue to decide if a SET for
        a readOnly or permanent row is accepted at all. In some
        contexts this may make sense, in others it may not. If
        a SET for a readOnly or permanent row is not accepted
        at all, then a 'wrongValue' error must be returned.
        "
        DEFVAL      { nonVolatile }
::= { usmUserEntry 12 }

vacmAccessContextMatch OBJECT-TYPE
        SYNTAX       INTEGER
        { exact (1), -- exact match of prefix and contextName
        prefix (2) -- Only match to the prefix
        }
        MAX-ACCESS   read-create
        STATUS       current
        DESCRIPTION "If the value of this object is exact(1), then all
        rows where the contextName exactly matches
        vacmAccessContextPrefix are selected.
        If the value of this object is prefix(2), then all
        rows where the contextName whose starting octets
        exactly match vacmAccessContextPrefix are selected.
        This allows for a simple form of wildcarding.
        "
        DEFVAL      { exact }
::= { vacmAccessEntry 4 }

vacmAccessNotifyViewName OBJECT-TYPE
        SYNTAX       SnmpAdminString (SIZE(0..32))
        MAX-ACCESS   read-create
        STATUS       current
        DESCRIPTION "The value of an instance of this object identifies
        the MIB view of the SNMP context to which this
        conceptual row authorizes access for notifications.
        The identified MIB view is that one for which the
        vacmViewTreeFamilyViewName has the same value as the
        instance of this object; if the value is the empty
        string or if there is no active MIB view having this
        value of vacmViewTreeFamilyViewName, then no access
        is granted.
        "
        DEFVAL      { ''H }   -- the empty string
::= { vacmAccessEntry 7 }

vacmAccessReadViewName OBJECT-TYPE
        SYNTAX       SnmpAdminString (SIZE(0..32))
        MAX-ACCESS   read-create
        STATUS       current
        DESCRIPTION "The value of an instance of this object identifies
        the MIB view of the SNMP context to which this
        conceptual row authorizes read access.
        The identified MIB view is that one for which the
        vacmViewTreeFamilyViewName has the same value as the
        instance of this object; if the value is the empty
        string or if there is no active MIB view having this
        value of vacmViewTreeFamilyViewName, then no access
        is granted.
        "
        DEFVAL      { ''H }   -- the empty string
::= { vacmAccessEntry 5 }

vacmAccessStatus OBJECT-TYPE
        SYNTAX       RowStatus
        MAX-ACCESS   read-create
        STATUS       current
        DESCRIPTION "The status of this conceptual row.
        The  RowStatus TC [RFC2579] requires that this
        DESCRIPTION clause states under which circumstances
        other objects in this row can be modified:
        The value of this object has no effect on whether
        other objects in this conceptual row can be modified.
        "
::= { vacmAccessEntry 9 }

vacmAccessStorageType OBJECT-TYPE
        SYNTAX       StorageType
        MAX-ACCESS   read-create
        STATUS       current
        DESCRIPTION "The storage type for this conceptual row.
        Conceptual rows having the value 'permanent' need not
        allow write-access to any columnar objects in the row.
        "
        DEFVAL      { nonVolatile }
::= { vacmAccessEntry 8 }

vacmAccessWriteViewName OBJECT-TYPE
        SYNTAX       SnmpAdminString (SIZE(0..32))
        MAX-ACCESS   read-create
        STATUS       current
        DESCRIPTION "The value of an instance of this object identifies
        the MIB view of the SNMP context to which this
        conceptual row authorizes write access.
        The identified MIB view is that one for which the
        vacmViewTreeFamilyViewName has the same value as the
        instance of this object; if the value is the empty
        string or if there is no active MIB view having this
        value of vacmViewTreeFamilyViewName, then no access
        is granted.
        "
        DEFVAL      { ''H }   -- the empty string
::= { vacmAccessEntry 6 }

vacmContextName  OBJECT-TYPE
        SYNTAX       SnmpAdminString (SIZE(0..32))
        MAX-ACCESS   read-only
        STATUS       current
        DESCRIPTION "A human readable name identifying a particular
        context at a particular SNMP entity.
        The empty contextName (zero length) represents the
        default context.
        "
::= { vacmContextEntry 1 }

vacmGroupName    OBJECT-TYPE
        SYNTAX       SnmpAdminString (SIZE(1..32))
        MAX-ACCESS   read-create
        STATUS       current
        DESCRIPTION "The name of the group to which this entry (e.g., the
        combination of securityModel and securityName)
        belongs.
        This groupName is used as index into the
        vacmAccessTable to select an access control policy.
        However, a value in this table does not imply that an
        instance with the value exists in table vacmAccesTable.
        "
::= { vacmSecurityToGroupEntry 3 }

vacmSecurityToGroupStatus OBJECT-TYPE
        SYNTAX       RowStatus
        MAX-ACCESS   read-create
        STATUS       current
        DESCRIPTION "The status of this conceptual row.
        Until instances of all corresponding columns are
        appropriately configured, the value of the
        corresponding instance of the vacmSecurityToGroupStatus
        column is 'notReady'.
        In particular, a newly created row cannot be made
        active until a value has been set for vacmGroupName.
        The  RowStatus TC [RFC2579] requires that this
        DESCRIPTION clause states under which circumstances
        other objects in this row can be modified:
        The value of this object has no effect on whether
        other objects in this conceptual row can be modified.
        "
::= { vacmSecurityToGroupEntry 5 }

vacmSecurityToGroupStorageType OBJECT-TYPE
        SYNTAX       StorageType
        MAX-ACCESS   read-create
        STATUS       current
        DESCRIPTION "The storage type for this conceptual row.
        Conceptual rows having the value 'permanent' need not
        allow write-access to any columnar objects in the row.
        "
        DEFVAL      { nonVolatile }
::= { vacmSecurityToGroupEntry 4 }

vacmViewSpinLock OBJECT-TYPE
        SYNTAX       TestAndIncr
        MAX-ACCESS   read-write
        STATUS       current
        DESCRIPTION "An advisory lock used to allow cooperating SNMP
        Command Generator applications to coordinate their
        use of the Set operation in creating or modifying
        views.
        When creating a new view or altering an existing
        view, it is important to understand the potential
        interactions with other uses of the view.  The
        vacmViewSpinLock should be retrieved.  The name of
        the view to be created should be determined to be
        unique by the SNMP Command Generator application by
        consulting the vacmViewTreeFamilyTable.  Finally,
        the named view may be created (Set), including the
        advisory lock.
        If another SNMP Command Generator application has
        altered the views in the meantime, then the spin
        lock's value will have changed, and so this creation
        will fail because it will specify the wrong value for
        the spin lock.
        Since this is an advisory lock, the use of this lock
        is not enforced.
        "
::= { vacmMIBViews 1 }

vacmViewTreeFamilyMask OBJECT-TYPE
        SYNTAX       OCTET STRING (SIZE (0..16))
        MAX-ACCESS   read-create
        STATUS       current
        DESCRIPTION "The bit mask which, in combination with the
        corresponding instance of vacmViewTreeFamilySubtree,
        defines a family of view subtrees.
        Each bit of this bit mask corresponds to a
        sub-identifier of vacmViewTreeFamilySubtree, with the
        most significant bit of the i-th octet of this octet
        string value (extended if necessary, see below)
        corresponding to the (8*i - 7)-th sub-identifier, and
        the least significant bit of the i-th octet of this
        octet string corresponding to the (8*i)-th
        sub-identifier, where i is in the range 1 through 16.
        Each bit of this bit mask specifies whether or not
        the corresponding sub-identifiers must match when
        determining if an OBJECT IDENTIFIER is in this
        family of view subtrees; a '1' indicates that an
        exact match must occur; a '0' indicates 'wild card',
        i.e., any sub-identifier value matches.
        Thus, the OBJECT IDENTIFIER X of an object instance
        is contained in a family of view subtrees if, for
        each sub-identifier of the value of
        vacmViewTreeFamilySubtree, either:
        the i-th bit of vacmViewTreeFamilyMask is 0, or
        the i-th sub-identifier of X is equal to the i-th
        sub-identifier of the value of
        vacmViewTreeFamilySubtree.
        If the value of this bit mask is M bits long and
        there are more than M sub-identifiers in the
        corresponding instance of vacmViewTreeFamilySubtree,
        then the bit mask is extended with 1's to be the
        required length.
        Note that when the value of this object is the
        zero-length string, this extension rule results in
        a mask of all-1's being used (i.e., no 'wild card'),
        and the family of view subtrees is the one view
        subtree uniquely identified by the corresponding
        instance of vacmViewTreeFamilySubtree.
        Note that masks of length greater than zero length
        do not need to be supported.  In this case this
        object is made read-only.
        "
        DEFVAL      { ''H }
::= { vacmViewTreeFamilyEntry 3 }

vacmViewTreeFamilyStatus OBJECT-TYPE
        SYNTAX       RowStatus
        MAX-ACCESS   read-create
        STATUS       current
        DESCRIPTION "The status of this conceptual row.
        The  RowStatus TC [RFC2579] requires that this
        DESCRIPTION clause states under which circumstances
        other objects in this row can be modified:
        The value of this object has no effect on whether
        other objects in this conceptual row can be modified.
        "
::= { vacmViewTreeFamilyEntry 6 }

vacmViewTreeFamilyStorageType OBJECT-TYPE
        SYNTAX       StorageType
        MAX-ACCESS   read-create
        STATUS       current
        DESCRIPTION "The storage type for this conceptual row.
        Conceptual rows having the value 'permanent' need not
        allow write-access to any columnar objects in the row.
        "
        DEFVAL      { nonVolatile }
::= { vacmViewTreeFamilyEntry 5 }

vacmViewTreeFamilyType OBJECT-TYPE
        SYNTAX       INTEGER  { included(1), excluded(2) }
        MAX-ACCESS   read-create
        STATUS       current
        DESCRIPTION "Indicates whether the corresponding instances of
        vacmViewTreeFamilySubtree and vacmViewTreeFamilyMask
        define a family of view subtrees which is included in
        or excluded from the MIB view.
        "
        DEFVAL      { included }
::= { vacmViewTreeFamilyEntry 4 }

END
